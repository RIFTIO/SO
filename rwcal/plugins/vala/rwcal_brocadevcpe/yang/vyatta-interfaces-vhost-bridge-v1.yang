module vyatta-interfaces-vhost-bridge-v1 {
	namespace "urn:vyatta.com:mgmt:vyatta-interfaces-vhost-bridge:1";
	prefix vyatta-interfaces-vhost-bridge-v1;

	import configd-v1 {
		prefix configd;
	}
	import vyatta-interfaces-v1 {
		prefix if;
	}
	import vyatta-interfaces-bridge-v1 {
		prefix interfaces-bridge;
	}
	import vyatta-interfaces-vhost-v1 {
		prefix interfaces-vhost;
	}
	import vyatta-interfaces-vhost-vif-v1 {
		prefix interfaces-vhost-vif;
	}

	organization "Brocade Communications Systems, Inc.";
	contact
		"Brocade Communications Systems, Inc.
                 Postal: 130 Holger Way
                         San Jose, CA 95134
                 E-mail: support@Brocade.com
                 Web: www.brocade.com";

	revision 2015-12-06 {
		description "Initial revision";
	}


	augment /if:interfaces/interfaces-vhost:vhost {
		uses interfaces-bridge:bridge-group;
	}
	augment /if:interfaces/interfaces-vhost:vhost/interfaces-vhost-vif:vif {
		uses interfaces-bridge:bridge-group {
			refine bridge-group {
				configd:end "vyatta-bridge.pl ${COMMIT_ACTION} $VAR(../../@).$VAR(../@)";
			}
		}
	}
}
