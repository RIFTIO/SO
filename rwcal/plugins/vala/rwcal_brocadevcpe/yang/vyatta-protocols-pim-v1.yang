module vyatta-protocols-pim-v1 {
	namespace "urn:vyatta.com:mgmt:vyatta-protocols-pim:1";
	prefix vyatta-protocols-pim-v1;

	import vyatta-types-v1 {
		prefix types;
	}
	import vyatta-protocols-v1 {
		prefix protocols;
	}
	import configd-v1 {
		prefix configd;
	}
	import vyatta-interfaces-v1 {
		prefix if;
	}
	import vyatta-interfaces-bridge-v1 {
		prefix interfaces-bridge;
	}
	import vyatta-interfaces-dataplane-v1 {
		prefix interfaces-dataplane;
	}
	import vyatta-interfaces-l2tpeth-v1 {
		prefix interfaces-l2tpeth;
	}
	import vyatta-interfaces-loopback-v1 {
		prefix interfaces-loopback;
	}
	import vyatta-interfaces-openvpn-v1 {
		prefix interfaces-openvpn;
	}
	import vyatta-interfaces-tunnel-v1 {
		prefix interfaces-tunnel;
	}
	import vyatta-interfaces-vti-v1 {
		prefix interfaces-vti;
	}
	import vyatta-protocols-pim-interface-v1  {
		prefix pim-interface;
	}
	import vyatta-interfaces-bonding-v1 {
		prefix interfaces-bonding;
	}

	organization "Brocade Communications Systems, Inc.";
	contact
		"Brocade Communications Systems, Inc.
		 Postal: 130 Holger Way
		         San Jose, CA 95134
		 E-mail: support@Brocade.com
		 Web: www.brocade.com";

	revision 2015-07-28 {
		description "New module, replaces vyatta-protocols-pim";
	}

	augment /protocols:protocols {
		container pim {
			configd:help "Protocol Independent Multicasting (PIM)";
			configd:priority "740";
			configd:validate "vyatta-pim-validate 4";
			configd:end "vyatta-pim 4";
			container register-source {
				configd:help "Configure the source address of Register packets sent by this DR";
				leaf interface {
					type string;
					configd:help "The name of the interface to use as the source of the register packets";
					configd:allowed "/opt/vyatta/share/tmplscripts/protocols/pim/register-source/interface/configd_allowed.sh";
				}
				leaf address {
					type types:ipv4-address;
					// Not multicast, reserved or loopback.
					must "(substring-before(., '.') < 224) and " +
						"(not(starts-with(., '127.')))" {
						error-message "Not a valid IPv4 unicast address.";
					}
					configd:help "IP address to use as the source of the register packets";
				}
			}
			container bsr-candidate {
				presence "true";
				configd:help "BSR-candidate configuration";
				leaf priority {
					type uint8;
					configd:help "Priority for a BSR candidate";
                    			default "64";
				}
				leaf interface {
					type string;
					configd:help "BSR-candidate interface name";
					configd:allowed "/opt/vyatta/share/tmplscripts/protocols/pim/bsr-candidate/interface/configd_allowed.sh";
					mandatory true;
				}
				leaf hash-mask {
					type uint32 {
						range 0..32 {
						}
					}
					configd:help "Hash mask length for RP selection";
                    			default "10";
				}
			}
			leaf ignore-rp-set-priority {
				type empty;
				configd:help "Ignore the RP-SET priority value, and use only the hashing mechanism for RP selection";
			}
			list anycast-rp {
				configd:help "Configure the Anycast RP in the RP set";
				key "tagnode";
				leaf tagnode {
					type  types:ipv4-address;
					// Not multicast, reserved or loopback.
					must "(substring-before(., '.') < 224) and " +
						"(not(starts-with(., '127.')))" {
						error-message "Not a valid IPv4 unicast address.";
					}
					configd:help "Configure the Anycast RP in the RP set";
				}
				leaf-list anycast-rp-peer {
					min-elements 1;
					type  types:ipv4-address;
					// Not multicast, reserved or loopback.
					must "(substring-before(., '.') < 224) and " +
						"(not(starts-with(., '127.')))" {
						error-message "Not a valid IPv4 unicast address.";
					}
					ordered-by "user";
					configd:help "Destination IP address where Register messages are copied and sent";
				}
			}
			leaf register-rp-reachability {
				type empty;
				configd:help "Enable the RP reachability check for PIM Registers at the DR";
			}
			container accept-register {
				configd:help "Configure the ability to filter out multicast sources specified by the given access-list at the RP";
				leaf list {
					type uint32 {
						range "100..199 | 2000..2699";
					}
					configd:help "Specify access list";
					configd:allowed "/opt/vyatta/share/tmplscripts/protocols/pim/accept-register/list/configd_allowed.sh";
				}
			}
			container spt-threshold {
				configd:help "Turn off the ability of the last-hop PIM router to switch to SPT";
				configd:allowed "/opt/vyatta/share/tmplscripts/protocols/pim/spt-threshold/group-list/configd_allowed.sh";
				container infinity {
					configd:help "Turn off the ability of the last-hop PIM router to switch to SPT";
					presence "Set SPT threshold to infinity";
					leaf group-list {
						type uint32 {
							range "1..99 | 1300..1999" {
							}
						}
						configd:help "Enable the ability for the last-hop PIM router to switch to SPT for multicast group addresses indicated by the given access-list";
						configd:allowed "/opt/vyatta/share/tmplscripts/protocols/pim/spt-threshold/group-list/configd_allowed.sh";
					}
				}
			}
			container legacy-register-checksum {
				presence "true";
				configd:help "Configure the option to calculate the register checksum over the whole packet";
				leaf group-list {
					type uint32 {
						range "1..99 | 1300..1999";
					}
					configd:help "Configure the option to calculate the register checksum over the whole packet on multicast groups specified by the access-list";
					configd:allowed "/opt/vyatta/share/tmplscripts/protocols/pim/legacy-register-checksum/group-list/configd_allowed.sh";
				}
			}
			leaf register-kat {
				type uint32 {
					range 1..65535 {
					}
				}
				configd:help "Configure a Keepalive Timer (KAT) value for (S,G) states at RP to monitor PIM register packets";
			}
			container rp-candidate {
				presence "need this for mandatory interface";
				configd:help "rp-candidate configuration";
				list interface {
				     	min-elements 1;
					configd:help "RP-candidate interface name";
					configd:allowed "/opt/vyatta/share/tmplscripts/protocols/pim/rp-candidate/interface/configd_allowed.sh";
					key "tagnode";
					leaf tagnode {
						type string;
						configd:help "RP-candidate interface name";
					}
					leaf priority {
						type uint8;
						configd:help "A candidate-RP priority";
					}
					leaf interval {
						type uint32 {
							range 1..16383 {
							}
						}
						configd:help "A candidate-RP advertisement interval";
					}
					leaf group-list {
						type uint32 {
							range 1..99 {
							}
						}
						configd:allowed "/opt/vyatta/share/tmplscripts/protocols/pim/rp-candidate/interface/group-list/configd_allowed.sh";
						configd:help "Specify the group ranges for this candidate RP";
					}
				}
			}
			leaf register-suppression-timer {
				type uint32 {
					range 11..65535 {
					}
				}
				configd:help "Configure the register-suppression time";
				default "60";
			}
			leaf join-prune-timer {
				type uint32 {
					range 1..65535 {
					}
				}
				configd:help "Set a PIM join/prune timer";
			}
			leaf register-rate-limit {
				type uint32 {
					range 1..65535 {
					}
				}
				configd:help "Configure the rate of Register packets sent by this designated router (DR)";
			}
			container ssm {
				configd:help "Configure Source Specific Multicast (SSM)";
				leaf default {
					type empty;
					configd:help "Define the 232/8 group range for SSM";
				}
				leaf range {
					type uint32 {
						range 1..99;
					}
					configd:help "Define an access-list for group range to use for SSM";
					configd:allowed "/opt/vyatta/share/tmplscripts/protocols/pim/ssm/range/configd_allowed.sh";
				}
			}
			list rp-address {
				configd:help "Statically configure an RP address for multicast groups";
				key "tagnode";
				leaf tagnode {
					type  types:ipv4-address;
					// Not multicast, reserved or loopback.
					must "(substring-before(., '.') < 224) and " +
						"(not(starts-with(., '127.')))" {
						error-message "Not a valid IPv4 unicast address.";
					}
					configd:help "Statically configure an RP address for multicast groups";
				}
				leaf list {
					type uint32 {
						range "1..99 | 1300..1999";
					}
					configd:help "Configure static-RP address for specific group ranges";
					configd:allowed "/opt/vyatta/share/tmplscripts/protocols/pim/rp-address/list/configd_allowed.sh";
				}
				leaf override {
					type empty;
					configd:help "Set to take precedence over dynamically learned mappings";
				}
			}
			container log {
				configd:help "Protocol Independent Multicast (PIM) logging parameters";
				leaf all {
					type empty;
					configd:help "Enable all PIM logs";
				}
				leaf events {
					type empty;
					configd:help "Enable PIM debugging for general configuration, Virtual Routing (VR)";
				}
				leaf mfc {
					type empty;
					configd:help "Enable PIM debugging for MFC updates";
				}
				leaf mib {
					type empty;
					configd:help "Enable PIM debugging for MIB entries";
				}
				leaf mtrace {
					type empty;
					configd:help "Enable PIM debugging for MTRACE messages";
				}
				leaf nexthop {
					type empty;
					configd:help "Enable PIM debugging for RPF neighbor nexthop cache handling";
				}
				leaf state {
					type empty;
					configd:help "Enable PIM debugging for PIM states";
				}
				leaf nsm {
					type empty;
					configd:help "Enable PIM debugging for PIM nsm";
				}
				leaf msdp {
					type empty;
					configd:help "Enable PIM debugging for PIM msdp";
				}
				container packet {
					configd:help "Enable PIM debugging for PIM packets";
					leaf all {
						type empty;
						configd:help "Enable PIM debugging for all PIM packets";
					}
					leaf send {
						type empty;
						configd:help "Enable PIM debugging for outgoing PIM packets";

					}
					leaf recv {
						type empty;
						configd:help "Enable PIM debugging for incoming PIM packets";
					}
				}
				container timer {
					configd:help "Enable PIM debugging for PIM timers";
					leaf all {
						type empty;
						configd:help "Enable PIM debugging for all PIM timers";
					}
					container assert {
						configd:help "Enable Protocol Independent Multicast (PIM) debugging for PIM assert timers";
						leaf all {
							type empty;
							configd:help "Enable Protocol Independent Multicast (PIM) debugging for all PIM assert timers";
						}
						leaf at {
							type empty;
							configd:help "Enable Protocol Independent Multicast (PIM) debugging for PIM Assert Timer";
						}
					}
					container bsr {
						configd:help "Enable Protocol Independent Multicast (PIM) debugging for PIM BSR timers";
						leaf all {
							type empty;
							configd:help "Enable Protocol Independent Multicast (PIM) debugging for all PIM BSR timers";
						}
						leaf bst {
							type empty;
							configd:help "Enable Protocol Independent Multicast (PIM) debugging for bootstrap Timer";
						}
						leaf crp {
							type empty;
							configd:help "Enable Protocol Independent Multicast (PIM) debugging for the Candidate-RP timer";
						}
					}
					container hello {
						configd:help "Enable Protocol Independent Multicast (PIM) debugging for various PIM timers";
						leaf all {
							type empty;
							configd:help "Enable Protocol Independent Multicast (PIM) debugging for all PIM hello timers";
						}
						leaf ht {
							type empty;
							configd:help "Enable Protocol Independent Multicast (PIM) debugging for PIM Hello timer";
						}
						leaf nlt {
							type empty;
							configd:help "Enable Protocol Independent Multicast (PIM) debugging for PIM Neighbor Liveliness timer";
						}
						leaf tht {
							type empty;
							configd:help "Enable Protocol Independent Multicast (PIM) debugging for Triggered Hello Timer";
						}
					}
					container joinprune {
						configd:help "Enable Protocol Independent Multicast (PIM) debugging for various PIM JoinPrune timers";
						leaf all {
							type empty;
							configd:help "Enable Protocol Independent Multicast (PIM) debugging for all PIM joinPrune timers";
						}
						leaf et {
							type empty;
							configd:help "Enable Protocol Independent Multicast (PIM) debugging for various PIM JoinPrune expiry timer";
						}
						leaf jt {
							type empty;
							configd:help "Enable Protocol Independent Multicast (PIM) debugging for various PIM JoinPrune upstream Join Timer";
						}
						leaf kat {
							type empty;
							configd:help "Enable Protocol Independent Multicast (PIM) debugging for various PIM JoinPrune Keep Alive timer";
						}
						leaf ot {
							type empty;
							configd:help "Enable Protocol Independent Multicast (PIM) debugging for various PIM JoinPrune Upstream Override Timer";
						}
						leaf ppt {
							type empty;
							configd:help "Enable Protocol Independent Multicast (PIM) debugging for various PIM JoinPrune timers PrunePending Timer";
						}
					}
					container register {
						configd:help "Enable Protocol Independent Multicast (PIM) debugging for various PIM register timer";
						leaf all {
							type empty;
							configd:help "Enable Protocol Independent Multicast (PIM) debugging for all PIM register timers";
						}
						leaf rst {
							type empty;
							configd:help "Enable Protocol Independent Multicast (PIM) debugging for various PIM Register Stop Timer";
						}
					}
				}
			}
		}
	}
	augment /if:interfaces/interfaces-bridge:bridge/interfaces-bridge:ip {
	        uses pim-interface:pim4-interface-parameters {
			refine pim {
				configd:validate "vyatta-pim-interface-validate 4 $VAR(../../@)";
				configd:end "vyatta-pim-interface 4 $VAR(../../@)";
			}
		}
	}
	augment /if:interfaces/interfaces-dataplane:dataplane/interfaces-dataplane:ip {
		uses pim-interface:pim4-interface-parameters {
			refine pim {
				configd:validate "vyatta-pim-interface-validate 4 $VAR(../../@)";
				configd:end "vyatta-pim-interface 4 $VAR(../../@)";
			}
		}
	}
	augment /if:interfaces/interfaces-dataplane:dataplane/interfaces-dataplane:vif/interfaces-dataplane:ip {
		uses pim-interface:pim4-interface-parameters {
		        refine pim {
		                configd:validate "vyatta-pim-interface-validate 4 $VAR(../../../@).$VAR(../../@)";
		                configd:end "vyatta-pim-interface 4 $VAR(../../../@).$VAR(../../@)";
			}
		}
	}
	augment /if:interfaces/interfaces-l2tpeth:l2tpeth/interfaces-l2tpeth:ip {
		uses pim-interface:pim4-interface-parameters {
			refine pim {
				configd:validate "vyatta-pim-interface-validate 4 $VAR(../../@)";
				configd:end "vyatta-pim-interface 4 $VAR(../../@)";
			}
		}
	}
	augment /if:interfaces/interfaces-l2tpeth:l2tpeth/interfaces-l2tpeth:vif/interfaces-l2tpeth:ip {
		uses pim-interface:pim4-interface-parameters {
		        refine pim{
		                configd:validate "vyatta-pim-interface-validate 4 $VAR(../../../@).$VAR(../../@)";
		                configd:end "vyatta-pim-interface 4 $VAR(../../../@).$VAR(../../@)";
			}
		}
	}
	augment /if:interfaces/interfaces-loopback:loopback/interfaces-loopback:ip {
		uses pim-interface:pim4-interface-parameters {
			refine pim {
				configd:validate "vyatta-pim-interface-validate 4 $VAR(../../@)";
				configd:end "vyatta-pim-interface 4 $VAR(../../@)";
			}
		}
	}
	augment /if:interfaces/interfaces-openvpn:openvpn/interfaces-openvpn:ip {
		uses pim-interface:pim4-interface-parameters {
			refine pim {
				configd:validate "vyatta-pim-interface-validate 4 $VAR(../../@)";
				configd:end "vyatta-pim-interface 4 $VAR(../../@)";
			}
		}
	}
	augment /if:interfaces/interfaces-tunnel:tunnel/interfaces-tunnel:ip {
		uses pim-interface:pim4-interface-parameters {
			refine pim {
				configd:validate "vyatta-pim-interface-validate 4 $VAR(../../@)";
				configd:end "vyatta-pim-interface 4 $VAR(../../@)";
			}
		}
	}
	augment /if:interfaces/interfaces-vti:vti/interfaces-vti:ip {
		uses pim-interface:pim4-interface-parameters {
			refine pim {
				configd:validate "vyatta-pim-interface-validate 4 $VAR(../../@)";
				configd:end "vyatta-pim-interface 4 $VAR(../../@)";
			}
		}
	}
	augment /if:interfaces/interfaces-bonding:bonding/interfaces-bonding:ip {
		uses pim-interface:pim4-interface-parameters {
			refine pim {
				configd:validate "vyatta-pim-interface-validate 4 $VAR(../../@)";
				configd:end "vyatta-pim-interface 4 $VAR(../../@)";
			}
		}
	}
	augment /if:interfaces/interfaces-bonding:bonding/interfaces-bonding:vif/interfaces-bonding:ip {
		uses pim-interface:pim4-interface-parameters {
		        refine pim {
		                configd:validate "vyatta-pim-interface-validate 4 $VAR(../../../@).$VAR(../../@)";
		                configd:end "vyatta-pim-interface 4 $VAR(../../../@).$VAR(../../@)";
			}
		}
	}
}
