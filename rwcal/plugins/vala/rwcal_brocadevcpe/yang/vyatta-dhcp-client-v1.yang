module vyatta-dhcp-client-v1 {
	namespace "urn:vyatta.com:mgmt:vyatta-dhcp-client:1";
	prefix vyatta-dhcp-client-v1;

	import configd-v1 {
	        prefix configd;
	}
	import vyatta-interfaces-v1 {
	        prefix if;
	}
	import vyatta-interfaces-bridge-v1 {
	        prefix interfaces-bridge;
	}
	import vyatta-interfaces-dataplane-v1 {
	        prefix interfaces-dataplane;
	}
	import vyatta-interfaces-bonding-v1 {
		prefix interfaces-bonding;
	}

	organization "Brocade Communications Systems, Inc.";
	contact
		"Brocade Communications Systems, Inc.
		 Postal: 130 Holger Way
		         San Jose, CA 95134
		 E-mail: support@Brocade.com
		 Web: www.brocade.com";

	revision 2015-08-14 {
		description "Initial revision of version 1.";
	}

	grouping interface-options {
		description "DHCP client interface options";
		leaf no-rfc3442 {
			type empty;
			configd:help "Disable request for RFC3442 classless static routes";
		}
	}

	grouping dhcp-options {
			container dhcp-options {
				configd:help "DHCP options";
				configd:end "dhcp-client-options $VAR(../@)";
				configd:validate "/opt/vyatta/share/tmplscripts/interfaces/dhcp-client-options/configd_validate1.cli";
				uses interface-options;
			}
	}

	grouping dhcp-options-vif {
			container dhcp-options {
				configd:help "DHCP options";
				configd:end "dhcp-client-options $VAR(../../@).$VAR(../@)";
				configd:validate "/opt/vyatta/share/tmplscripts/interfaces/dhcp-client-options/configd_validate1.cli";
				uses interface-options;
			}
	}

	augment /if:interfaces/interfaces-bridge:bridge {
		uses dhcp-options;
	}

	augment /if:interfaces/interfaces-dataplane:dataplane {
		uses dhcp-options;
	}

	augment /if:interfaces/interfaces-dataplane:dataplane/interfaces-dataplane:vif {
		uses dhcp-options-vif;
	}
	augment /if:interfaces/interfaces-bonding:bonding {
		uses dhcp-options;
	}

	augment /if:interfaces/interfaces-bonding:bonding/interfaces-bonding:vif {
		uses dhcp-options-vif;
	}
}
