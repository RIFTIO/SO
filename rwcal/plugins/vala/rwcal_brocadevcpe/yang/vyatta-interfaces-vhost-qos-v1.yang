module vyatta-interfaces-vhost-qos-v1 {
	namespace "urn:vyatta.com:mgmt:vyatta-interfaces-vhost-qos:1";
	prefix vyatta-interfaces-vhost-qos-v1;

	import configd-v1 {
		prefix configd;
	}
	import vyatta-interfaces-v1 {
		prefix if;
	}
	import vyatta-interfaces-vhost-policy-v1 {
		prefix policy;
	}
	import vyatta-interfaces-vhost-v1 {
		prefix interfaces-vhost;
	}
	import vyatta-interfaces-vhost-vif-v1 {
		prefix vif;
	}

	organization "Brocade Communications Systems, Inc.";
	contact
		"Brocade Communications Systems, Inc.
                 Postal: 130 Holger Way
                         San Jose, CA 95134
                 E-mail: support@Brocade.com
                 Web: www.brocade.com";

	revision 2015-09-29 {
		description "Initial revision";
	}

	augment /if:interfaces/interfaces-vhost:vhost {
		configd:end "/opt/vyatta/sbin/qos-policy.pl --update-binding $VAR(@)";
	}

	augment /if:interfaces/interfaces-vhost:vhost/policy:policy {
		leaf qos {
			type string;
			configd:help "Qos policy for interface";
			configd:allowed "echo $VAR(/policy/qos/name/@@)";
			configd:validate "qos-policy.pl --validate-binding $VAR(../../@) 0";
		}
	}
	augment /if:interfaces/interfaces-vhost:vhost/vif:vif/policy:policy {
		leaf qos {
			type string;
			configd:help "Qos policy for virtual interface";
			configd:allowed "echo $VAR(/policy/qos/name/@@)";
			configd:validate "qos-policy.pl --validate-binding $VAR(../../../@) $VAR(../../@)";
		}
	}
}
