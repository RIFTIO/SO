module vyatta-policy-pbr-bridge-v1 {
	namespace "urn:vyatta.com:mgmt:vyatta-policy-pbr-bridge:1";
	prefix policy-pbr-bridge;

	import vyatta-interfaces-v1 {
		prefix if;
	}
	import vyatta-interfaces-bridge-v1 {
                prefix interfaces-bridge;
	}
	import vyatta-interfaces-bridge-policy-v1 {
		prefix interfaces-bridge-policy;
	}
	import vyatta-policy-pbr-v1 {
		prefix policy-pbr;
	}

	organization "Brocade Communications Systems, Inc.";
	contact
		"Brocade Communications Systems, Inc.
		 Postal: 130 Holger Way
		         San Jose, CA 95134
		 E-mail: support@Brocade.com
		 Web: www.brocade.com";

	revision 2015-10-08 {
		description "Initial revision.";
	}

	augment /if:interfaces/interfaces-bridge:bridge/interfaces-bridge-policy:policy {
		uses policy-pbr:pbr-if-parameters;
	}
}
