module vyatta-protocols-igmp-v1 {
	namespace "urn:vyatta.com:mgmt:vyatta-protocols-igmp:1";
	prefix vyatta-protocols-igmp-v1;

	import vyatta-types-v1 {
		prefix types;
	}
	import vyatta-protocols-v1 {
		prefix protocols;
	}
	import configd-v1 {
		prefix configd;
	}
	import vyatta-interfaces-v1 {
		prefix if;
	}
	import vyatta-interfaces-bridge-v1 {
		prefix interfaces-bridge;
	}
	import vyatta-interfaces-dataplane-v1 {
		prefix interfaces-dataplane;
	}
	import vyatta-interfaces-l2tpeth-v1 {
		prefix interfaces-l2tpeth;
	}
	import vyatta-interfaces-loopback-v1 {
		prefix interfaces-loopback;
	}
	import vyatta-interfaces-openvpn-v1 {
		prefix interfaces-openvpn;
	}
	import vyatta-interfaces-tunnel-v1 {
		prefix interfaces-tunnel;
	}
	import vyatta-interfaces-vti-v1 {
		prefix interfaces-vti;
	}
	import vyatta-interfaces-bonding-v1 {
		prefix interfaces-bonding;
	}

	organization "Brocade Communications Systems, Inc.";
	contact
		"Brocade Communications Systems, Inc.
		 Postal: 130 Holger Way
		         San Jose, CA 95134
		 E-mail: support@Brocade.com
		 Web: www.brocade.com";

	revision 2016-01-13 {
		description "Added and updated help text under the static-group list";
	}
	revision 2015-07-28 {
		description "New module, replaces vyatta-protocols-igmp";
	}

         typedef static-group-source {
                type union {
                        type string {
                                configd:pattern-help "ssm-map";
                                configd:help "Use SSM mapping";
                        }
                        type types:ipv4-address;
                }
        }

	grouping igmp-interface-parameters {
		 container igmp {
		 	presence "true";
		        configd:help "Internet Group Management Protocol (IGMP)";
			configd:priority "760";
			container querier {
				presence "true";
			        configd:help "Querier mode";
				leaf forced {
					type empty;
				        configd:help "Set forced querier mode";
				}
				leaf querier-timeout {
					type uint32 {
						range 60..300;
					}
					configd:help "Period that router waits before assuming querier role";
				}
			}
			leaf offlink {
				type empty;
				configd:help "Enable off-link for IGMP";
			}
			leaf startup-query-interval {
				type uint32 {
					range 1..18000;
				}
				configd:help "Configure a query interval value for IGMP";
			}
			container immediate-leave {
				configd:help "Immediate leave feature";
				leaf group-list {
					type uint32 {
					     range "1..99 | 1300..1999";
					}
					configd:help "Defines multicast groups in which the immediate leave feature is enabled";
				configd:allowed "/opt/vyatta/share/tmplscripts/interfaces/all/ip/igmp/immediate-leave/group-list/configd_allowed.sh";
				}
			}
			leaf robustness-variable {
				type uint32 {
					range 2..7;
				}
				configd:help "configure the robustness variable value on an interface";
			}
			leaf limit-exception {
				type uint32 {
					range "1..99 | 1300..1999";
				}
				configd:help "Specify access-list that defines multicast groups that are exempted from being subject to configured limit";
				configd:allowed "/opt/vyatta/share/tmplscripts/interfaces/all/ip/igmp/limit-exception/configd_allowed.sh";
			}
			leaf limit {
				type uint32 {
					range 1..2097152;
				}
				default 5000;
				configd:help "Configure the limit on the maximum number of group membership states";
			}
			leaf query-max-response-time {
				type uint32 {
					range 1..240;
				}
				configd:help "configure the maximum response time advertised in IGMP queries";
				default "10";
			}
			leaf last-member-query-count {
				type uint32 {
					range 2..7;
				}
				configd:help "Set the last-member query-count value";
			}
			list static-group {
				configd:help "Configure a static multicast group membership";
				key "tagnode";
				leaf tagnode {
					type types:ipv4-address;
					// non-reserved multicast address
					must "(substring-before(., '.') >= 224) and " +
						"(substring-before(., '.') <= 239) and " +
						"(not(starts-with(., '224.0.0')))" {
						error-message "Not a valid IPv4 multicast address.";
					}
					configd:help "Configure a static multicast group membership";
				}
				leaf-list source {
					type static-group-source;
					//not (multicast, loopback) or ssm-map
					must "(substring-before(., '.') < 224) and " +
						"(not(starts-with(., '127.'))) or " +
						"(. = 'ssm-map')" {
						error-message "Not either a valid IPv4 unicast address or <ssm-map>.";
					}
					ordered-by "user";
					configd:help "Configure standard IP source address as a static source from where multicast packets originate";
				}
			}
			list join-group {
				configd:help "Configure a join multicast group";
				key "tagnode";
				leaf tagnode {
					type types:ipv4-address;
					// non-reserved multicast address
					must "(substring-before(., '.') >= 224) and " +
						"(substring-before(., '.') <= 239) and " +
						"(not(starts-with(., '224.0.0')))" {
						error-message "Not a valid IPv4 multicast address.";
					}
					configd:help "Configure a join multicast group";
				}
				leaf-list source {
					type types:ipv4-address;
					// not multicast reserved or loopback.
					must "(substring-before(., '.') < 224) and " +
						"(not(starts-with(., '127.')))" {
						error-message "Not a valid IPv4 unicast address.";
					}
					configd:help "Standard IP source address to be configured as a source from where multicast packets originate";
				}
			}
			leaf last-member-query-interval {
				type uint32 {
					range 1000..25500;
				}
				configd:help "Configure the frequency at which the router sends IGMP group-specific host query messages";
			}
			leaf version {
				type uint32 {
					range 1..3;
				}
				default "3";
				configd:help "Configure the current IGMP protocol version on an interface";
			}
			leaf access-group {
				type uint32 {
					range 1..99 {
					}
				}
				configd:help "Control the multicast local-membership groups learned on an interface";
				configd:allowed "/opt/vyatta/share/tmplscripts/interfaces/all/ip/igmp/access-group/configd_allowed.sh";
			}
			leaf enforce-router-alert {
				type empty;
				configd:help "Enable strict RA (Router Advertisement) validation for IGMP";
			}
			leaf query-interval {
				type uint32 {
					range 2..18000;
				}
				configd:help "Configure the frequency of sending IGMP host query messages";
				default "126";
			}
			leaf startup-query-count {
				type uint32 {
					range 2..10;
				}
				configd:help "Configure a startup query count for IGMP";
			}
		 }
	}

	augment /protocols:protocols {
		container igmp {
			configd:validate "vyatta-igmp-validate 4";
			configd:end "vyatta-igmp 4";
			configd:help "Internet Group Management Protocol (IGMP)";
			leaf limit-exception {
				type uint32 {
					range "1..99 | 1300..1999";
				}
				configd:help "Specify access-list that defines multicast groups that are exempted from being subject to configured limit";
				configd:allowed "/opt/vyatta/share/tmplscripts/protocols/igmp/limit-exception/configd_allowed.sh";
			}
			leaf limit {
				type uint32 {
					range 1..2097152;
				}
				configd:help "Configure the limit on the maximum number of group membership states";
			}
			container ssm-map {
				presence "true";
				configd:help "Enable SSM mapping on the router";
				container static {
					configd:help "Configure the static mode of defining SSM mapping";
					list access-list {
						configd:help "Configure access-list for the static mode of defining SSM mapping";
						configd:allowed "/opt/vyatta/share/tmplscripts/protocols/igmp/ssm-map/static/access-list/configd_allowed.sh";
						key "tagnode";
						leaf tagnode {
							type uint32 {
								range "1..99 | 1300..1999";
							}
							configd:help "Configure access-list for the static mode of defining SSM mapping";
							configd:allowed "/opt/vyatta/share/tmplscripts/protocols/igmp/ssm-map/static/access-list/configd_allowed.sh";
						}
						leaf-list source {
							min-elements 1;
							type types:ipv4-address;
							// not multicast reserved or loopback.
							must "(substring-before(., '.') < 224) and " +
								"(not(starts-with(., '127.')))" {
								error-message "Not a valid IPv4 unicast address.";
							}
							ordered-by "user";
							configd:help "Configure source address to use for static map group";
						}
					}
				}
			}
			container log {
				configd:help "IGMP logging parameters";
				leaf all {
					type empty;
					configd:help "Enable all IGMP debugging";
				}
				leaf encode {
					type empty;
					configd:help "Enable IGMP encode debugging";
				}
				leaf decode {
					type empty;
					configd:help "Enable IGMP decode debugging";
				}
				leaf events {
					type empty;
					configd:help "Enable IGMP events debugging";
				}
				leaf fsm {
					type empty;
					configd:help "Enable IGMP fsm debugging";
				}
				leaf tib {
					type empty;
					configd:help "Enable IGMP tib debugging";
				}
			}
		}
	}

	augment /if:interfaces/interfaces-bridge:bridge/interfaces-bridge:ip {
		uses igmp-interface-parameters {
			refine igmp {
			configd:validate "vyatta-igmp-interface-validate $VAR(../../@)";
			configd:end "vyatta-igmp-interface $VAR(../../@)";
			}
		}
	}
	augment /if:interfaces/interfaces-dataplane:dataplane/interfaces-dataplane:ip {

		uses igmp-interface-parameters {
			refine igmp {
			configd:validate "vyatta-igmp-interface-validate $VAR(../../@)";
			configd:end "vyatta-igmp-interface $VAR(../../@)";
			}
		}
	}
	augment /if:interfaces/interfaces-dataplane:dataplane/interfaces-dataplane:vif/interfaces-dataplane:ip {
		uses igmp-interface-parameters {
			refine igmp {
			configd:validate "vyatta-igmp-interface-validate $VAR(../../../@).$VAR(../../@)";
			configd:end "vyatta-igmp-interface $VAR(../../../@).$VAR(../../@)";
			}
		}
	}
	augment /if:interfaces/interfaces-l2tpeth:l2tpeth/interfaces-l2tpeth:ip {
		uses igmp-interface-parameters {
			refine igmp {
			configd:validate "vyatta-igmp-interface-validate $VAR(../../@)";
			configd:end "vyatta-igmp-interface $VAR(../../@)";
			}
		}
	}
	augment /if:interfaces/interfaces-l2tpeth:l2tpeth/interfaces-l2tpeth:vif/interfaces-l2tpeth:ip {
		uses igmp-interface-parameters {
			refine igmp {
			configd:validate "vyatta-igmp-interface-validate $VAR(../../../@).$VAR(../../@)";
			configd:end "vyatta-igmp-interface $VAR(../../../@).$VAR(../../@)";
			}
		}
	}
	augment /if:interfaces/interfaces-loopback:loopback/interfaces-loopback:ip {
		uses igmp-interface-parameters {
			refine igmp {
			configd:validate "vyatta-igmp-interface-validate $VAR(../../@)";
			configd:end "vyatta-igmp-interface $VAR(../../@)";
			}
		}
	}
	augment /if:interfaces/interfaces-openvpn:openvpn/interfaces-openvpn:ip {
		uses igmp-interface-parameters {
			refine igmp {
			configd:validate "vyatta-igmp-interface-validate $VAR(../../@)";
			configd:end "vyatta-igmp-interface $VAR(../../@)";
			}
		}
	}
	augment /if:interfaces/interfaces-tunnel:tunnel/interfaces-tunnel:ip {
		uses igmp-interface-parameters {
			refine igmp {
			configd:validate "vyatta-igmp-interface-validate $VAR(../../@)";
			configd:end "vyatta-igmp-interface $VAR(../../@)";
			}
		}
	}
	augment /if:interfaces/interfaces-vti:vti/interfaces-vti:ip {
		uses igmp-interface-parameters {
			refine igmp {
			configd:validate "vyatta-igmp-interface-validate $VAR(../../@)";
			configd:end "vyatta-igmp-interface $VAR(../../@)";
			}
		}
	}
	augment /if:interfaces/interfaces-bonding:bonding/interfaces-bonding:ip {
		uses igmp-interface-parameters {
			refine igmp {
			configd:validate "vyatta-igmp-interface-validate $VAR(../../@)";
			configd:end "vyatta-igmp-interface $VAR(../../@)";
			}
		}
	}
	augment /if:interfaces/interfaces-bonding:bonding/interfaces-bonding:vif/interfaces-bonding:ip {
		uses igmp-interface-parameters {
			refine igmp {
			configd:validate "vyatta-igmp-interface-validate $VAR(../../../@).$VAR(../../@)";
			configd:end "vyatta-igmp-interface $VAR(../../../@).$VAR(../../@)";
			}
		}
	}
}
