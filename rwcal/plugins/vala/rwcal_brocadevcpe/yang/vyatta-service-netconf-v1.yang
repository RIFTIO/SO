module vyatta-service-netconf-v1 {
	namespace "urn:vyatta.com:mgmt:vyatta-service-netconf:1";
	prefix vyatta-service-netconf-v1;

	import vyatta-services-v1 {
		prefix service;
	}
	import configd-v1 {
		prefix configd;
	}

	organization "Brocade Communications Systems, Inc.";
	contact
		"Brocade Communications Systems, Inc.
		 Postal: 130 Holger Way
		         San Jose, CA 95134
		 E-mail: support@Brocade.com
		 Web: www.brocade.com";

	revision 2015-08-10 {
		description "Initial release of v1.";
	}

	augment /service:service {
		container netconf {
			presence "netconf";
			configd:priority "501";
			configd:help "NETCONF (RFC 6241)";
			configd:end "/opt/vyatta/share/tmplscripts/service/netconf/configd_end.sh";
			configd:validate "/opt/vyatta/share/tmplscripts/service/netconf/configd_validate1.cli";
			leaf disable {
				type empty;
				configd:help "Disable NETCONF service";
			}
		}
	}
}
