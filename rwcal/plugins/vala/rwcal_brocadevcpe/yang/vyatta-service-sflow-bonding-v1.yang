module vyatta-service-sflow-bonding-v1 {
	namespace "urn:vyatta.com:mgmt:vyatta-service-sflow-bonding:1";
	prefix vyatta-service-sflow-bonding-v1;

	import configd-v1 {
		prefix configd;
	}
	import vyatta-interfaces-v1 {
		prefix if;
	}
	import vyatta-interfaces-bonding-v1 {
		prefix if-bonding;
	}

	organization "Brocade Communications Systems, Inc.";
	contact
		"Brocade Communications Systems, Inc.
		 Postal: 130 Holger Way
		         San Jose, CA 95134
		 E-mail: support@Brocade.com
		 Web: www.brocade.com";

	revision 2015-09-15 {
		description "Initial revision of version 1.";
	}

	augment /if:interfaces/if-bonding:bonding {
		leaf sflow {
			type empty;
			configd:help "Enable/Disable sflow for interface";
			configd:delete "vplane-sflow.pl --cmd=disable --intf=$VAR(../@) --type=$VAR(..)";
			configd:update "vplane-sflow.pl --cmd=enable --intf=$VAR(../@) --type=$VAR(..)";
		}
	}
}
