module vyatta-policy-v1 {
	namespace "urn:vyatta.com:mgmt:vyatta-policy:1";
	prefix vyatta-policy-v1;

	import configd-v1 {
		prefix configd;
	}

	organization "Brocade Communications Systems, Inc.";
	contact
		"Brocade Communications Systems, Inc.
		 Postal: 130 Holger Way
		 	 San Jose, CA 95134
		 E-mail: support@Brocade.com
		 Web: www.brocade.com";

	revision 2015-08-05 {
		description "Initial revision of version 1.";
	}

	container policy {
		configd:help "PBR, QoS, and routing policy";
	}

	grouping policy-binding {
		container policy {
			configd:help "Policy bindings";
		}
	}

}
