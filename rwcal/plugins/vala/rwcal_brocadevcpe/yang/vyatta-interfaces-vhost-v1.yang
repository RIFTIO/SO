module vyatta-interfaces-vhost-v1 {
	namespace "urn:vyatta.com:mgmt:vyatta-interfaces-vhost:1";
	prefix vyatta-interfaces-vhost-v1;

	import vyatta-interfaces-v1 {
		prefix if;
	}
	import configd-v1 {
		prefix configd;
	}
	import vyatta-types-v1 {
		prefix types;
	}

	organization "Brocade Communications Systems, Inc.";
	contact
		"Brocade Communications Systems, Inc.
		Postal: 130 Holger Way
			San Jose, CA 95134
		E-mail: support@Brocade.com
		Web: www.brocade.com";

	revision 2016-03-16 {
		description "Single quote the regex pattern";
	}

	revision 2015-08-26 {
		description "Initial revision";
	}

	augment /if:interfaces {
		list vhost {
			configd:defer-actions "ifmgrctl register $VAR(@)";
			configd:end "vyatta-intf-end $VAR(@)";
			configd:priority 318;
			configd:help "Virtio vhost devices";
			key name;
			leaf name {
				configd:help "Virtio vhost devices";
				type types:interface-ifname {
					pattern 'dp[0-9]+vhost[0-9]+'; //for now
				}
			}
			uses if:if-parameters;
			leaf-list address {
				type if:address-dhcp;
				ordered-by "user";
				configd:help "IP address";
				configd:create "vyatta-address add $VAR(../@) $VAR(@)";
				configd:allowed "echo 'dhcp dhcpv6 <>'";
			}
		}
	}
}
