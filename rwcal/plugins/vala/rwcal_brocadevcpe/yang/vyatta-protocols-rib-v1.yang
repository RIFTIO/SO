module vyatta-protocols-rib-v1 {
	namespace "urn:vyatta.com:mgmt:vyatta-protocols-rib:1";
	prefix vyatta-protocols-rib-v1;

	import vyatta-protocols-v1 {
		prefix protocols;
	}
	import configd-v1 {
		prefix configd;
	}

	organization "Brocade Communications Systems, Inc.";
	contact
		"Brocade Communications Systems, Inc.
		 Postal: 130 Holger Way
		         San Jose, CA 95134
		 E-mail: support@Brocade.com
		 Web: www.brocade.com";

	revision 2015-08-06 {
		description "Initial revision of version 1";
	}

	augment /protocols:protocols {
		container rib {
			configd:priority "650";
			configd:help "Routing Information Base (RIB) parameters";
			container log {
				configd:help "RIB logging parameters";
				leaf all {
					type empty;
					configd:help "Enable all RIB logs";
					configd:create "/opt/vyatta/share/tmplscripts/protocols/rib/log/configd_create.sh";
				  configd:delete "/opt/vyatta/share/tmplscripts/protocols/rib/log/configd_delete.pl $VAR(@)";

				}
				leaf events {
					type empty;
					configd:help "Enable RIB events logs";
					configd:create "/opt/vyatta/share/tmplscripts/protocols/rib/log/configd_create.sh";
					configd:delete "/opt/vyatta/share/tmplscripts/protocols/rib/log/configd_delete.pl $VAR(@)";
				}
				leaf nsm {
					type empty;
					configd:help "Enable RIB nsm logs";
					configd:create "/opt/vyatta/share/tmplscripts/protocols/rib/log/configd_create.sh";
					configd:delete "/opt/vyatta/share/tmplscripts/protocols/rib/log/configd_delete.pl $VAR(@)";
				}
				leaf kernel {
					type empty;
					configd:help "Enable RIB kernel logs";
					configd:create "/opt/vyatta/share/tmplscripts/protocols/rib/log/configd_create.sh";
					configd:delete "/opt/vyatta/share/tmplscripts/protocols/rib/log/configd_delete.pl $VAR(@)";
				}
				container packet {
					configd:help "RIB packet logs";
					leaf all {
						type empty;
						configd:help "Enable RIB packet all logs";
						configd:create "/opt/vyatta/share/tmplscripts/protocols/rib/log/packet/configd_create.sh";
					 	configd:delete "/opt/vyatta/share/tmplscripts/protocols/rib/log/configd_delete.pl $VAR(../@) $VAR(@)";
					}
					leaf detail {
						type empty;
						configd:help "Enable RIB packet detail logs";
						configd:create "/opt/vyatta/share/tmplscripts/protocols/rib/log/packet/configd_create.sh";
				          	configd:delete "/opt/vyatta/share/tmplscripts/protocols/rib/log/configd_delete.pl $VAR(../@) $VAR(@)";
					}
					leaf send {
						type empty;
						configd:help "Enable RIB packet send logs";
						configd:create "/opt/vyatta/share/tmplscripts/protocols/rib/log/packet/configd_create.sh";
				   	configd:delete "/opt/vyatta/share/tmplscripts/protocols/rib/log/configd_delete.pl $VAR(../@) $VAR(@)";
					}
					leaf recv {
						type empty;
						configd:help "Enable RIB packet recv logs";
						configd:create "/opt/vyatta/share/tmplscripts/protocols/rib/log/packet/configd_create.sh";
				   	configd:delete "/opt/vyatta/share/tmplscripts/protocols/rib/log/configd_delete.pl $VAR(../@) $VAR(@)";
					}
				}
			}
		}
	}
}
