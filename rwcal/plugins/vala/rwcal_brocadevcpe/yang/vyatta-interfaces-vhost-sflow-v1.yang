module vyatta-interfaces-vhost-sflow-v1 {
	namespace "urn:vyatta.com:mgmt:vyatta-interfaces-vhost-sflow:1";
	prefix vyatta-interfaces-vhost-sflow-v1;

	import vyatta-interfaces-v1 {
		prefix if;
	}
	import vyatta-interfaces-vhost-v1 {
		prefix if-vhost;
	}
	import configd-v1 {
		prefix configd;
	}

	organization "Brocade Communications Systems, Inc.";
	contact
		"Brocade Communications Systems, Inc.
		Postal: 130 Holger Way
			San Jose, CA 95134
		E-mail: support@Brocade.com
		Web: www.brocade.com";

	revision 2015-08-26 {
		description "Initial revision";
	}

	augment /if:interfaces/if-vhost:vhost {
		leaf sflow {
			type empty;
			configd:help "Enable/Disable sflow for interface";
			configd:delete "vplane-sflow.pl --cmd=disable --intf=$VAR(../@)";
			configd:update "vplane-sflow.pl --cmd=enable --intf=$VAR(../@)";
		}
	}
}
