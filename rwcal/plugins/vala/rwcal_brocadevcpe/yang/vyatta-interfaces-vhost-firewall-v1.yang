module vyatta-interfaces-vhost-firewall-v1 {
	namespace "urn:vyatta.com:mgmt:vyatta-interfaces-vhost-firewall:1";
	prefix vyatta-interfaces-vhost-firewall-v1;

	import vyatta-interfaces-v1 {
		prefix if;
	}
	import vyatta-security-firewall-v1 {
		prefix fw;
	}
	import vyatta-interfaces-vhost-v1 {
		prefix interfaces-vhost;
	}
	import vyatta-interfaces-vhost-vif-v1 {
		prefix vif;
	}

	organization "Brocade Communications Systems, Inc.";
	contact
		"Brocade Communications Systems, Inc.
                 Postal: 130 Holger Way
                         San Jose, CA 95134
                 E-mail: support@Brocade.com
                 Web: www.brocade.com";

	revision 2015-09-29 {
		description "Initial revision";
	}


	augment /if:interfaces/interfaces-vhost:vhost {
		uses fw:firewall-if-parameters;
	}
	augment /if:interfaces/interfaces-vhost:vhost/vif:vif {
		uses fw:firewall-vif-if-parameters;
	}
}
