module vyatta-system-acm-v1 {
	namespace "urn:vyatta.com:mgmt:vyatta-system-acm:1";
	prefix vyatta-system-acm-v1;

	import vyatta-system-v1 {
		prefix system;
	}
	import configd-v1 {
		prefix configd;
	}

	organization "Brocade Communications Systems, Inc.";
	contact
		"Brocade Communications Systems, Inc.
		 Postal: 130 Holger Way
		         San Jose, CA 95134
		 E-mail: support@Brocade.com
		 Web: www.brocade.com";

	revision 2016-03-25 {
		description "Only run config rule-set update";
	}
	revision 2015-08-05 {
		description "Initial revision of version 1.";
	}

	augment /system:system {
		container acm {
			configd:help "Access Control Management";
			configd:end "vyatta-update-configruleset.pl";
		}
	}
}
