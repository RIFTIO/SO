module vyatta-openvpn-access-server-v1 {
	namespace "urn:vyatta.com:mgmt:vyatta-openvpn-access-server:1";
	prefix vyatta-openvpn-access-server-v1;

	import vyatta-interfaces-v1 {
		prefix if;
	}
	import vyatta-interfaces-openvpn-v1 {
		prefix interfaces-openvpn;
	}
	import configd-v1 {
		prefix configd;
	}

	organization "Brocade Communications Systems, Inc.";
	contact
		"Brocade Communications Systems, Inc.
		 Postal: 130 Holger Way
		         San Jose, CA 95134
		 E-mail: support@Brocade.com
		 Web: www.brocade.com";

	revision 2015-08-14 {
		description "Initial revision of version 1.";
	}

	augment /if:interfaces/interfaces-openvpn:openvpn {
		container remote-configuration {
			presence "true";
			configd:help "Configure openvpn remote configuration";
			configd:delete "/opt/vyatta/share/tmplscripts/interfaces/openvpn/remote-configuration/configd_delete.sh";
			leaf tunnel-username {
				type string;
				configd:help "Optional username to establish tunnel (with autologin disabled)";
			}
			leaf tunnel-password {
				type string;
				configd:secret "true";
				configd:help "Optional password to establish tunnel (with autologin disabled)";
			}
			leaf password {
				type string;
				configd:secret "true";
				configd:help "Optional password to access remote openvpn configuration server";
			}
			leaf username {
				type string;
				configd:help "Optional username to access remote openvpn configuration server";
			}
			leaf server {
				type string;
				configd:help "Remote openvpn configuration server";
			}
		}
	}
}
