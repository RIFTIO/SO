module vyatta-service-flow-monitoring-vhost-v1 {
	namespace "urn:vyatta.com:mgmt:vyatta-service-flow-monitoring-vhost:1";
	prefix service-vhost-flow-monitor;

	import vyatta-interfaces-v1 {
		prefix if;
	}
	import vyatta-interfaces-vhost-v1 {
		prefix if-vhost;
	}
	import vyatta-service-flow-monitoring-v1 {
		prefix flow-monitoring;
	}

	organization "Brocade Communications Systems, Inc.";
	contact
		"Brocade Communications Systems, Inc.
                 Postal: 130 Holger Way
                         San Jose, CA 95134
                 E-mail: support@Brocade.com
                 Web: www.brocade.com";

	revision 2015-09-29 {
		description "Initial revision";
	}

	augment /if:interfaces/if-vhost:vhost {
		uses flow-monitoring:interface-parameters;
	}
}
