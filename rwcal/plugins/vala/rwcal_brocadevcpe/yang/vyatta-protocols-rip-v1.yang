module vyatta-protocols-rip-v1 {
	namespace "urn:vyatta.com:mgmt:vyatta-protocols-rip:1";
	prefix vyatta-protocols-rip-v1;

	import vyatta-types-v1 {
		prefix types;
	}
	import vyatta-protocols-v1 {
		prefix protocols;
	}
	import configd-v1 {
		prefix configd;
	}
	import vyatta-interfaces-v1 {
		prefix if;
	}
	import vyatta-interfaces-bridge-v1 {
		prefix interfaces-bridge;
	}
	import vyatta-interfaces-dataplane-v1 {
		prefix interfaces-dataplane;
	}
	import vyatta-interfaces-l2tpeth-v1 {
		prefix interfaces-l2tpeth;
	}
	import vyatta-interfaces-loopback-v1 {
		prefix interfaces-loopback;
	}
	import vyatta-interfaces-openvpn-v1 {
		prefix interfaces-openvpn;
	}
	import vyatta-interfaces-tunnel-v1 {
		prefix interfaces-tunnel;
	}
	import vyatta-interfaces-vti-v1 {
		prefix interfaces-vti;
	}
	import vyatta-interfaces-bonding-v1 {
		prefix interfaces-bonding;
	}

	organization "Brocade Communications Systems, Inc.";
	contact
		"Brocade Communications Systems, Inc.
		 Postal: 130 Holger Way
		         San Jose, CA 95134
		 E-mail: support@Brocade.com
		 Web: www.brocade.com";

	revision 2014-08-06 {
		description "Initial revision of version 1";
	}

	augment /protocols:protocols {
		container rip {
			presence "true";
			configd:priority "650";
			configd:help "Routing Information Protocol (RIP) parameters";
			configd:create "/opt/vyatta/share/tmplscripts/protocols/rip/configd_create.sh";
			configd:delete "/opt/vyatta/share/tmplscripts/protocols/rip/configd_delete.sh";
			leaf-list route {
				type types:ipv4-prefix {
					configd:syntax "/opt/vyatta/share/tmplscripts/protocols/rip/route/configd_syntax1.cli";
				}
				ordered-by "user";
				configd:help "RIP static route";
				configd:create "/opt/vyatta/share/tmplscripts/protocols/rip/route/configd_create1.cli";
				configd:delete "/opt/vyatta/share/tmplscripts/protocols/rip/route/configd_delete1.cli";
			}
			container timers {
				presence "true";
				configd:help "RIP timer values";
				configd:end "/opt/vyatta/share/tmplscripts/protocols/rip/timers/configd_end.sh";
				leaf garbage-collection {
					type uint32 {
						range 5..2147483647 {
							error-message "Garbage collection timer must be between 5 and 2147483647";
						}
					}
					default "120";
					configd:help "Garbage collection timer";
				}
				leaf update {
					type uint32 {
						range 5..2147483647 {
							error-message "Update timer must be between 5 and 2147483647";
						}
					}
					default "30";
					configd:help "Routing table update timer";
				}
				leaf timeout {
					type uint32 {
						range 5..2147483647 {
							error-message "Timeout timer must be between 5 and 2147483647";
						}
					}
					default "180";
					configd:help "Routing information timeout timer";
				}
			}
			container distribute-list {
				presence "true";
				configd:help "Filter networks in routing updates";
				container access-list {
					presence "true";
					configd:help "Access list";
					leaf out {
						type uint32 {
							configd:syntax "/opt/vyatta/share/tmplscripts/protocols/rip/distribute-list/access-list/out/configd_syntax1.cli";
						}
						configd:help "Access list to apply to output packets";
						configd:validate "/opt/vyatta/share/tmplscripts/protocols/rip/distribute-list/access-list/out/configd_validate1.cli";
						configd:update "/opt/vyatta/share/tmplscripts/protocols/rip/distribute-list/access-list/out/configd_update1.cli";
						configd:delete "/opt/vyatta/share/tmplscripts/protocols/rip/distribute-list/access-list/out/configd_delete1.cli";
					}
					leaf in {
						type uint32 {
							configd:syntax "/opt/vyatta/share/tmplscripts/protocols/rip/distribute-list/access-list/in/configd_syntax1.cli";
						}
						configd:help "Access list to apply to input packets";
						configd:validate "/opt/vyatta/share/tmplscripts/protocols/rip/distribute-list/access-list/in/configd_validate1.cli";
						configd:update "/opt/vyatta/share/tmplscripts/protocols/rip/distribute-list/access-list/in/configd_update1.cli";
						configd:delete "/opt/vyatta/share/tmplscripts/protocols/rip/distribute-list/access-list/in/configd_delete1.cli";
					}
				}
				list interface {
					configd:help "Apply filtering to an interface";
					configd:allowed "/opt/vyatta/share/tmplscripts/protocols/rip/distribute-list/interface/configd_allowed.sh";
					configd:validate "/opt/vyatta/share/tmplscripts/protocols/rip/distribute-list/interface/configd_validate.cli";
					key "tagnode";
					leaf tagnode {
						type string {
							configd:syntax "/opt/vyatta/share/tmplscripts/protocols/rip/distribute-list/interface/configd_syntax1.cli";
						}
						configd:help "Apply filtering to an interface";
						configd:allowed "/opt/vyatta/share/tmplscripts/protocols/rip/distribute-list/interface/configd_allowed.sh";
					}
					container access-list {
						presence "true";
						configd:help "Access list";
						leaf out {
							type uint32;
							configd:help "Access list to apply to output packets";
							configd:validate "/opt/vyatta/share/tmplscripts/protocols/rip/distribute-list/interface/access-list/out/configd_validate1.cli";
							configd:update "/opt/vyatta/share/tmplscripts/protocols/rip/distribute-list/interface/access-list/out/configd_update1.cli";
							configd:delete "/opt/vyatta/share/tmplscripts/protocols/rip/distribute-list/interface/access-list/out/configd_delete1.cli";
						}
						leaf in {
							type uint32;
							configd:help "Access list to apply to input packets";
							configd:validate "/opt/vyatta/share/tmplscripts/protocols/rip/distribute-list/interface/access-list/in/configd_validate1.cli";
							configd:update "/opt/vyatta/share/tmplscripts/protocols/rip/distribute-list/interface/access-list/in/configd_update1.cli";
							configd:delete "/opt/vyatta/share/tmplscripts/protocols/rip/distribute-list/interface/access-list/in/configd_delete1.cli";
						}
					}
					container prefix-list {
						presence "true";
						configd:help "Prefix-list";
						leaf out {
							type string;
							configd:help "Prefix-list to apply to output packets";
							configd:validate "/opt/vyatta/share/tmplscripts/protocols/rip/distribute-list/interface/prefix-list/out/configd_validate1.cli";
							configd:update "/opt/vyatta/share/tmplscripts/protocols/rip/distribute-list/interface/prefix-list/out/configd_update1.cli";
							configd:delete "/opt/vyatta/share/tmplscripts/protocols/rip/distribute-list/interface/prefix-list/out/configd_delete1.cli";
						}
						leaf in {
							type string;
							configd:help "Prefix-list to apply to input packets";
							configd:validate "/opt/vyatta/share/tmplscripts/protocols/rip/distribute-list/interface/prefix-list/in/configd_validate1.cli";
							configd:update "/opt/vyatta/share/tmplscripts/protocols/rip/distribute-list/interface/prefix-list/in/configd_update1.cli";
							configd:delete "/opt/vyatta/share/tmplscripts/protocols/rip/distribute-list/interface/prefix-list/in/configd_delete1.cli";
						}
					}
				}
				container prefix-list {
					presence "true";
					configd:help "Prefix-list";
					leaf out {
						type string;
						configd:help "Prefix-list to apply to output packets";
						configd:validate "/opt/vyatta/share/tmplscripts/protocols/rip/distribute-list/prefix-list/out/configd_validate1.cli";
						configd:update "/opt/vyatta/share/tmplscripts/protocols/rip/distribute-list/prefix-list/out/configd_update1.cli";
						configd:delete "/opt/vyatta/share/tmplscripts/protocols/rip/distribute-list/prefix-list/out/configd_delete1.cli";
					}
					leaf in {
						type string;
						configd:help "Prefix-list to apply to input packets";
						configd:validate "/opt/vyatta/share/tmplscripts/protocols/rip/distribute-list/prefix-list/in/configd_validate1.cli";
						configd:update "/opt/vyatta/share/tmplscripts/protocols/rip/distribute-list/prefix-list/in/configd_update1.cli";
						configd:delete "/opt/vyatta/share/tmplscripts/protocols/rip/distribute-list/prefix-list/in/configd_delete1.cli";
					}
				}
			}
			leaf-list passive-interface {
				type string {
					configd:syntax "/opt/vyatta/share/tmplscripts/protocols/rip/passive-interface/configd_syntax1.cli";
				}
				ordered-by "user";
				configd:help "Suppress routing updates on an interface";
				configd:create "/opt/vyatta/share/tmplscripts/protocols/rip/passive-interface/configd_create.sh";
				configd:delete "/opt/vyatta/share/tmplscripts/protocols/rip/passive-interface/configd_delete.sh";
				configd:allowed "/opt/vyatta/share/tmplscripts/protocols/rip/passive-interface/configd_allowed.sh";
				configd:validate "/opt/vyatta/share/tmplscripts/protocols/rip/passive-interface/configd_validate.cli";
			}
			leaf default-metric {
				type uint32 {
					range 1..16 {
						error-message "Must be between 1-16";
					}
				}
				configd:help "Metric of redistributed routes";
				configd:update "/opt/vyatta/share/tmplscripts/protocols/rip/default-metric/configd_update1.cli";
				configd:delete "/opt/vyatta/share/tmplscripts/protocols/rip/default-metric/configd_delete1.cli";
			}
			leaf-list interface {
				type types:interface-ifname;
				ordered-by "user";
				configd:help "Interface name";
				configd:allowed "/opt/vyatta/share/tmplscripts/protocols/rip/interface/configd_allowed.sh";
				configd:create "/opt/vyatta/share/tmplscripts/protocols/rip/interface/configd_create.sh";
				configd:delete "/opt/vyatta/share/tmplscripts/protocols/rip/interface/configd_delete.sh";
			}
			leaf-list neighbor {
				type types:ipv4-address;
				ordered-by "user";
				configd:help "Neighbor router";
				configd:create "/opt/vyatta/share/tmplscripts/protocols/rip/neighbor/configd_create1.cli";
				configd:delete "/opt/vyatta/share/tmplscripts/protocols/rip/neighbor/configd_delete1.cli";
			}
			container redistribute {
				presence "true";
				configd:help "Redistribute information from another routing protocol";
				container bgp {
					presence "true";
					configd:help "Redistribute BGP routes";
					configd:end "/opt/vyatta/share/tmplscripts/protocols/rip/redistribute/configd_redist_end.cli";
					leaf route-map {
						type string;
						configd:help "Route map reference";
						configd:validate "/opt/vyatta/share/tmplscripts/protocols/rip/redistribute/configd_redist_routemap_validate.cli";
					}
					leaf metric {
						type uint32 {
							range 1..16 {
								error-message "metric must be between 1 and 16";
							}
						}
						configd:help "Metric for redistributed routes";
					}
				}
				container kernel {
					presence "true";
					configd:help "Redistribute kernel routes";
					configd:end "/opt/vyatta/share/tmplscripts/protocols/rip/redistribute/configd_redist_end.cli";
					leaf route-map {
						type string;
						configd:help "Route map reference";
						configd:validate "/opt/vyatta/share/tmplscripts/protocols/rip/redistribute/configd_redist_routemap_validate.cli";
					}
					leaf metric {
						type uint32 {
							range 1..16 {
								error-message "metric must be between 1 and 16";
							}
						}
						configd:help "Metric for redistributed routes";
					}
				}
				container connected {
					presence "true";
					configd:help "Redistribute connected routes";
					configd:end "/opt/vyatta/share/tmplscripts/protocols/rip/redistribute/configd_redist_end.cli";
					leaf route-map {
						type string;
						configd:help "Route map reference";
						configd:validate "/opt/vyatta/share/tmplscripts/protocols/rip/redistribute/configd_redist_routemap_validate.cli";
					}
					leaf metric {
						type uint32 {
							range 1..16 {
								error-message "metric must be between 1 and 16";
							}
						}
						configd:help "Metric for redistributed routes";
					}
				}
				container static {
					presence "true";
					configd:help "Redistribute static routes";
					configd:end "/opt/vyatta/share/tmplscripts/protocols/rip/redistribute/configd_redist_end.cli";
					leaf route-map {
						type string;
						configd:help "Route map reference";
						configd:validate "/opt/vyatta/share/tmplscripts/protocols/rip/redistribute/configd_redist_routemap_validate.cli";
					}
					leaf metric {
						type uint32 {
							range 1..16 {
								error-message "metric must be between 1 and 16";
							}
						}
						configd:help "Metric for redistributed routes";
					}
				}
				container ospf {
					presence "true";
					configd:help "Redistribute OSPF routes";
					configd:end "/opt/vyatta/share/tmplscripts/protocols/rip/redistribute/configd_redist_end.cli";
					leaf route-map {
						type string;
						configd:help "Route map reference";
						configd:validate "/opt/vyatta/share/tmplscripts/protocols/rip/redistribute/configd_redist_routemap_validate.cli";
					}
					leaf metric {
						type uint32 {
							range 1..16 {
								error-message "metric must be between 1 and 16";
							}
						}
						configd:help "Metric for redistributed routes";
					}
				}
			}
			container default-information {
				presence "true";
				configd:help "Control distribution of default route";
				leaf originate {
					type empty;
					configd:help "Distribute a default route";
					configd:create "/opt/vyatta/share/tmplscripts/protocols/rip/default-information/originate/configd_create1.cli";
					configd:delete "/opt/vyatta/share/tmplscripts/protocols/rip/default-information/originate/configd_delete1.cli";
				}
			}
			list network-distance {
				configd:help "Administrative distance for network";
				key "tagnode";
				leaf tagnode {
					type types:ipv4-prefix {
						configd:syntax "/opt/vyatta/share/tmplscripts/protocols/rip/network-distance/configd_syntax1.cli";
					}
					configd:help "Source network prefix";
				}
				leaf distance {
					type uint32 {
						range 1..255;
					}
					configd:help "Administrative distance for network";
					configd:create "/opt/vyatta/share/tmplscripts/protocols/rip/network-distance/distance/configd_create.sh";
					configd:delete "/opt/vyatta/share/tmplscripts/protocols/rip/network-distance/distance/configd_delete.sh";
				}
				leaf access-list {
					type string;
					configd:help "Access list";
					configd:create "/opt/vyatta/share/tmplscripts/protocols/rip/network-distance/access-list/configd_create.sh";
					configd:delete "/opt/vyatta/share/tmplscripts/protocols/rip/network-distance/access-list/configd_delete.sh";
					configd:validate "/opt/vyatta/share/tmplscripts/protocols/rip/network-distance/access-list/configd_validate1.cli";
					configd:validate "/opt/vyatta/share/tmplscripts/protocols/rip/network-distance/access-list/configd_validate2.cli";
				}
			}
			leaf version {
				type uint32 {
					range 1..2 {}
				}
				configd:help "RIP version";
				configd:update "/opt/vyatta/share/tmplscripts/protocols/rip/version/configd_update.sh";
				configd:delete "/opt/vyatta/share/tmplscripts/protocols/rip/version/configd_delete.sh";
			}
			leaf default-distance {
				type uint32 {
					range 1..255 {
						error-message "must be between 1 and 255";
					}
				}
				configd:help "Administrative distance";
				configd:update "/opt/vyatta/share/tmplscripts/protocols/rip/default-distance/configd_update1.cli";
				configd:delete "/opt/vyatta/share/tmplscripts/protocols/rip/default-distance/configd_delete1.cli";
			}
			leaf-list network {
				type union {
					type types:ipv4-address;
					type types:ipv4-prefix;
				}
				ordered-by "user";
				configd:help "RIP network";
				configd:create "/opt/vyatta/share/tmplscripts/protocols/rip/network/configd_create1.cli";
				configd:delete "/opt/vyatta/share/tmplscripts/protocols/rip/network/configd_delete1.cli";
			}
			container log {
				configd:help "RIP logging parameters";
				leaf all {
					type empty;
					configd:help "Enable all RIP logs";
					configd:create "/opt/vyatta/share/tmplscripts/protocols/rip/log/configd_create.sh";
					configd:delete "/opt/vyatta/share/tmplscripts/protocols/rip/log/configd_delete.pl $VAR(@)";
				}
				leaf events {
					type empty;
					configd:help "Enable RIP events logs";
					configd:create "/opt/vyatta/share/tmplscripts/protocols/rip/log/configd_create.sh";
					configd:delete "/opt/vyatta/share/tmplscripts/protocols/rip/log/configd_delete.pl $VAR(@)";
				}
				leaf rib {
					type empty;
					configd:help "Enable RIP rib logs";
					configd:create "/opt/vyatta/share/tmplscripts/protocols/rip/log/configd_create.sh";
					configd:delete "/opt/vyatta/share/tmplscripts/protocols/rip/log/configd_delete.pl $VAR(@)";
				}
				leaf nsm {
					type empty;
					configd:help "Enable RIP nsm logs";
					configd:create "/opt/vyatta/share/tmplscripts/protocols/rip/log/configd_create.sh";
					configd:delete "/opt/vyatta/share/tmplscripts/protocols/rip/log/configd_delete.pl $VAR(@)";
				}
				container packet {
					configd:help "RIP packet logs";
					leaf all {
						type empty;
						configd:help "Enable RIP packet all logs";
						configd:create "/opt/vyatta/share/tmplscripts/protocols/rip/log/packet/configd_create.sh";
						configd:delete "/opt/vyatta/share/tmplscripts/protocols/rip/log/configd_delete.pl $VAR(../@) $VAR(@)";
					}
					leaf send {
						type empty;
						configd:help "Enable RIP packet send logs";
						configd:create "/opt/vyatta/share/tmplscripts/protocols/rip/log/packet/configd_create.sh";
						configd:delete "/opt/vyatta/share/tmplscripts/protocols/rip/log/configd_delete.pl $VAR(../@) $VAR(@)";
					}
					leaf recv {
						type empty;
						configd:help "Enable RIP packet recv logs";
						configd:create "/opt/vyatta/share/tmplscripts/protocols/rip/log/packet/configd_create.sh";
						configd:delete "/opt/vyatta/share/tmplscripts/protocols/rip/log/configd_delete.pl $VAR(../@) $VAR(@)";
					}
					leaf detail {
						type empty;
						configd:help "Enable RIP packet detail logs";
						configd:create "/opt/vyatta/share/tmplscripts/protocols/rip/log/packet/configd_create.sh";
						configd:delete "/opt/vyatta/share/tmplscripts/protocols/rip/log/configd_delete.pl $VAR(../@) $VAR(@)";
					}
				}
			}
		}
	}
	grouping itf-ip-rip {
		container rip {
			configd:help "Routing Information Protocol (RIP)";
			container split-horizon {
				presence "true";
				configd:help "Split horizon parameters";
				configd:end "/opt/vyatta/share/tmplscripts/interfaces/all/ip/rip/split-horizon/configd_end.sh";
				configd:delete "/opt/vyatta/share/tmplscripts/interfaces/all/ip/rip/split-horizon/configd_delete.sh";
				leaf poison-reverse {
					type empty;
					configd:help "Enable poison reverse for split-horizon";
					configd:create "/opt/vyatta/share/tmplscripts/interfaces/all/ip/rip/split-horizon/poison-reverse/configd_create.sh";
					configd:delete "/opt/vyatta/share/tmplscripts/interfaces/all/ip/rip/split-horizon/poison-reverse/configd_delete.sh";
					configd:validate "/opt/vyatta/share/tmplscripts/interfaces/all/ip/rip/split-horizon/poison-reverse/configd_validate1.cli";
				}
				leaf disable {
					type empty;
					configd:help "Disable split horizon on specified interface";
					configd:create "/opt/vyatta/share/tmplscripts/interfaces/all/ip/rip/split-horizon/disable/configd_create.sh";
					configd:delete "/opt/vyatta/share/tmplscripts/interfaces/all/ip/rip/split-horizon/disable/configd_delete.sh";
					configd:validate "/opt/vyatta/share/tmplscripts/interfaces/all/ip/rip/split-horizon/disable/configd_validate1.cli";
				}
			}
			container receive {
				presence "true";
				configd:help "RIP Advertisement receive options";
				leaf version {
					type enumeration {
						enum "1";
						enum "2";
						enum "both";
					}
					configd:help "Receive specified version of RIP packets on an interface";
					configd:update "/opt/vyatta/share/tmplscripts/interfaces/all/ip/rip/receive/version/configd_update.sh";
					configd:delete "/opt/vyatta/share/tmplscripts/interfaces/all/ip/rip/receive/version/configd_delete.sh";
				}
			}
			container authentication {
				presence "true";
				configd:help "Authentication method";
				leaf plaintext-password {
					type string {
						pattern '[^\t\n\r ]{1,16}' {
							error-message "Password must be 16 characters or less";
						}
					}
					configd:secret "true";
					configd:help "Plain text password";
					configd:update "/opt/vyatta/share/tmplscripts/interfaces/all/ip/rip/authentication/plaintext-password/configd_update.sh";
					configd:delete "/opt/vyatta/share/tmplscripts/interfaces/all/ip/rip/authentication/plaintext-password/configd_delete.sh";
					configd:validate "/opt/vyatta/share/tmplscripts/interfaces/all/ip/rip/authentication/plaintext-password/configd_validate1.cli";
				}
				list md5 {
					configd:help "MD5 authentication parameters";
					configd:validate "/opt/vyatta/share/tmplscripts/interfaces/all/ip/rip/authentication/md5/configd_validate1.cli";
					key "tagnode";
					leaf tagnode {
						type uint32 {
							range 1..255 {
								error-message "ID must be between 1 and 255";
							}
						}
						configd:help "MD5 authentication parameters";
					}
					leaf password {
						type string {
							pattern '[^\t\n\r ]{1,16}' {
								error-message "MD5 key must be 16 characters or less";
							}
						}
						configd:help "Authentication password";
						configd:update "/opt/vyatta/share/tmplscripts/interfaces/all/ip/rip/authentication/md5/password/configd_update.sh";
						configd:delete "/opt/vyatta/share/tmplscripts/interfaces/all/ip/rip/authentication/md5/password/configd_delete.sh";
					}
				}
			}
			container send {
				presence "true";
				configd:help "RIP Advertisement transmission options";
				leaf version {
					type enumeration {
						enum "1";
						enum "2";
						enum "both";
					}
					configd:help "Send specified version of RIP packets on an interface";
					configd:update "/opt/vyatta/share/tmplscripts/interfaces/all/ip/rip/send/version/configd_update.sh";
					configd:delete "/opt/vyatta/share/tmplscripts/interfaces/all/ip/rip/send/version/configd_delete.sh";
				}
			}
		}
	}
	augment /if:interfaces/interfaces-bridge:bridge/interfaces-bridge:ip {
		uses itf-ip-rip;
	}
	augment /if:interfaces/interfaces-dataplane:dataplane/interfaces-dataplane:ip {
		uses itf-ip-rip;
	}
	augment /if:interfaces/interfaces-dataplane:dataplane/interfaces-dataplane:vif/interfaces-dataplane:ip {
		uses itf-ip-rip;
	}
	augment /if:interfaces/interfaces-l2tpeth:l2tpeth/interfaces-l2tpeth:ip {
		uses itf-ip-rip;
	}
	augment /if:interfaces/interfaces-l2tpeth:l2tpeth/interfaces-l2tpeth:vif/interfaces-l2tpeth:ip {
		uses itf-ip-rip;
	}
	augment /if:interfaces/interfaces-loopback:loopback/interfaces-loopback:ip {
		uses itf-ip-rip;
	}
	augment /if:interfaces/interfaces-openvpn:openvpn/interfaces-openvpn:ip {
		uses itf-ip-rip;
	}
	augment /if:interfaces/interfaces-tunnel:tunnel/interfaces-tunnel:ip {
		uses itf-ip-rip;
	}
	augment /if:interfaces/interfaces-vti:vti/interfaces-vti:ip {
		uses itf-ip-rip;
	}
	augment /if:interfaces/interfaces-bonding:bonding/interfaces-bonding:ip {
		uses itf-ip-rip;
	}
	augment /if:interfaces/interfaces-bonding:bonding/interfaces-bonding:vif/interfaces-bonding:ip {
		uses itf-ip-rip;
	}
}
