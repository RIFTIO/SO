module vyatta-protocols-ospf-v1 {
	namespace "urn:vyatta.com:mgmt:vyatta-protocols-ospf:1";
	prefix vyatta-protocols-ospf-v1;

	import vyatta-protocols-v1 {
		prefix protocols;
	}
	import vyatta-services-v1 {
		prefix service;
	}
	import vyatta-service-snmp-v1 {
		prefix service-snmp;
	}
	import vyatta-types-v1 {
		prefix types;
	}
	import configd-v1 {
		prefix configd;
	}
	import vyatta-interfaces-v1 {
		prefix if;
	}
	import vyatta-interfaces-bridge-v1 {
		prefix interfaces-bridge;
	}
	import vyatta-interfaces-dataplane-v1 {
		prefix interfaces-dataplane;
	}
	import vyatta-interfaces-l2tpeth-v1 {
		prefix interfaces-l2tpeth;
	}
	import vyatta-interfaces-loopback-v1 {
		prefix interfaces-loopback;
	}
	import vyatta-interfaces-openvpn-v1 {
		prefix interfaces-openvpn;
	}
	import vyatta-interfaces-tunnel-v1 {
		prefix interfaces-tunnel;
	}
	import vyatta-interfaces-vti-v1 {
		prefix interfaces-vti;
	}
	import vyatta-interfaces-bonding-v1 {
		prefix interfaces-bonding;
	}

	organization "Brocade Communications Systems, Inc.";
	contact
		"Brocade Communications Systems, Inc.
		 Postal: 130 Holger Way
		         San Jose, CA 95134
		 E-mail: support@Brocade.com
		 Web: www.brocade.com";

	revision 2016-05-09 {
		description "Various configd script changes.";
	}

	revision 2015-09-30 {
		description "Initial revision of version 1";
	}

    grouping parameters_redistribute {
        leaf metric-type {
            type uint32 {
                range 1..2;
            }
            configd:help "Metric type for redistributed routes";
            default "2";
        }
        leaf route-map {
            type string;
                configd:help "Route map reference";
                configd:validate "/opt/vyatta/share/tmplscripts/protocols/ospf/configd_route_map_validate.cli";
                configd:allowed "/opt/vyatta/share/tmplscripts/protocols/ospf/configd_route_map_allowed.sh";
            }
        leaf metric {
            type uint32 {
                range 0..16777214;
            }
            configd:help "Metric for redistributed routes";
        }
        leaf tag {
            type uint32 {
                range 1..2147483647;
            }
            configd:help "Tag for redistributed routes";
        }
    }

	augment /protocols:protocols {
		container ospf {
			presence "true";
			configd:priority "620";
			configd:help "Open Shortest Path First protocol (OSPF) parameters";
			configd:begin "/opt/vyatta/share/tmplscripts/protocols/ospf/configd_begin.sh";
			configd:end "/opt/vyatta/share/tmplscripts/protocols/ospf/configd_end.sh";
			container parameters {
				presence "true";
				configd:help "OSPF specific parameters";
				leaf opaque-lsa {
					type empty;
					configd:help "Enable the Opaque-LSA capability (rfc2370)";
					configd:create "/opt/vyatta/share/tmplscripts/protocols/ospf/parameters/opaque-lsa/configd_create1.cli";
					configd:delete "/opt/vyatta/share/tmplscripts/protocols/ospf/parameters/opaque-lsa/configd_delete1.cli";
				}
				leaf abr-type {
					type enumeration {
						enum "cisco" {
							configd:help "Cisco ABR type (default)";
						}
						enum "ibm" {
							configd:help "Ibm ABR type";
						}
						enum "shortcut" {
							configd:help "Shortcut ABR type";
						}
						enum "standard" {
							configd:help "Standard ABR type";
						}
					}
					configd:help "OSPF ABR type";
					default "cisco";
					configd:update "/opt/vyatta/share/tmplscripts/protocols/ospf/parameters/abr-type/configd_update.sh";
					configd:delete "/opt/vyatta/share/tmplscripts/protocols/ospf/parameters/abr-type/configd_delete.sh";
				}
				leaf router-id {
					type types:ipv4-address;
					configd:help "Override the default router identifier";
					configd:validate "/opt/vyatta/share/tmplscripts/protocols/ospf/parameters/router-id/configd_validate.cli";
				}
				leaf rfc1583-compatibility {
					type empty;
					configd:help "Enable rfc1583 criteria for handling AS external routes";
					configd:create "/opt/vyatta/share/tmplscripts/protocols/ospf/parameters/rfc1583-compatibility/configd_create.sh";
					configd:delete "/opt/vyatta/share/tmplscripts/protocols/ospf/parameters/rfc1583-compatibility/configd_delete.sh";
				}
			}
			list distribute-list {
				configd:help "Access list to filter networks in routing updates";
				key "tagnode";
				leaf tagnode {
					type uint32 {
						configd:syntax "/opt/vyatta/share/tmplscripts/protocols/ospf/distribute-list/configd_syntax1.cli";
					}
					configd:help "Access list to filter networks in routing updates";
				}
				leaf-list export {
					type enumeration {
						enum "bgp";
						enum "connected";
						enum "kernel";
						enum "rip";
						enum "static";
					}
					ordered-by "user";
					configd:help "Filter for outgoing routing updates [REQUIRED]";
					configd:create "/opt/vyatta/share/tmplscripts/protocols/ospf/distribute-list/export/configd_create.sh";
					configd:delete "/opt/vyatta/share/tmplscripts/protocols/ospf/distribute-list/export/configd_delete.sh";
					configd:validate "/opt/vyatta/share/tmplscripts/protocols/ospf/distribute-list/export/configd_validate1.cli";
					configd:validate "/opt/vyatta/share/tmplscripts/protocols/ospf/distribute-list/export/configd_validate2.cli";
				}
				leaf import {
					type empty;
					configd:help "Filter for incoming routing updates";
					configd:create "/opt/vyatta/share/tmplscripts/protocols/ospf/distribute-list/import/configd_create.sh";
					configd:delete "/opt/vyatta/share/tmplscripts/protocols/ospf/distribute-list/import/configd_delete.sh";
					configd:validate "/opt/vyatta/share/tmplscripts/protocols/ospf/distribute-list/import/configd_validate1.cli";
				}
			}
			leaf-list passive-interface {
				type string;
				ordered-by "user";
				configd:priority "621";
				configd:help "Suppress routing updates on an interface";
				configd:allowed "/opt/vyatta/share/tmplscripts/protocols/ospf/passive-interface/configd_allowed.sh";
				configd:create "/opt/vyatta/share/tmplscripts/protocols/ospf/passive-interface/configd_create.sh";
				configd:delete "/opt/vyatta/share/tmplscripts/protocols/ospf/passive-interface/configd_delete.sh";
				configd:validate "/opt/vyatta/share/tmplscripts/protocols/ospf/passive-interface/configd_validate.cli";
			}
			leaf-list passive-interface-exclude {
				type string;
				ordered-by "user";
				configd:priority "622";
				configd:help "Excludes OSPF routing update suppression on an interface";
				configd:allowed "/opt/vyatta/sbin/vyatta-interfaces.pl --show all --filter-out ^ers";
				configd:create "/opt/vyatta/share/tmplscripts/protocols/ospf/passive-interface/exclude/configd_create.sh";
				configd:delete "/opt/vyatta/share/tmplscripts/protocols/ospf/passive-interface/exclude/configd_delete.sh";
				configd:validate "/opt/vyatta/share/tmplscripts/protocols/ospf/passive-interface/exclude/configd_validate.cli";
			}
			leaf default-metric {
				type uint32 {
					range 1..16777214;
				}
				configd:help "Metric of redistributed routes";
				configd:create "/opt/vyatta/share/tmplscripts/protocols/ospf/default-metric/configd_create.sh";
				configd:delete "/opt/vyatta/share/tmplscripts/protocols/ospf/default-metric/configd_delete.sh";
			}
			container refresh {
				presence "true";
				configd:help "Adjust refresh parameters";
				leaf timers {
					type uint32 {
						range 10..1800;
					}
					configd:help "Refresh timer";
					configd:update "/opt/vyatta/share/tmplscripts/protocols/ospf/refresh/timers/configd_update.sh";
					configd:delete "/opt/vyatta/share/tmplscripts/protocols/ospf/refresh/timers/configd_delete.sh";
				}
			}
			list neighbor {
				configd:help "Neighbor IP address";
				configd:begin "/opt/vyatta/share/tmplscripts/protocols/ospf/neighbor/configd_begin.sh";
				configd:delete "/opt/vyatta/share/tmplscripts/protocols/ospf/neighbor/configd_delete.sh";
				key "tagnode";
				leaf tagnode {
					type types:ipv4-address;
					configd:help "Neighbor IP address";
				}
				leaf priority {
					type uint32 {
						range 0..255;
					}
					configd:help "Neighbor priority in seconds";
					default "0";
				}
				leaf poll-interval {
					type uint32 {
						range 1..65535;
					}
					configd:help "Dead neighbor polling interval";
					default "120";
				}
			}
            container redistribute {
                configd:help "Redistribute information from another routing protocol";
                container bgp {
                    presence "true";
                    configd:help "Redistribute bgp routes";
                    configd:end "/opt/vyatta/share/tmplscripts/protocols/ospf/redistribute/configd_end.sh";
                    uses parameters_redistribute;
                }    
                container kernel {
                    presence "true";
                    configd:help "Redistribute kernel routes";
                    configd:end "/opt/vyatta/share/tmplscripts/protocols/ospf/redistribute/configd_end.sh";
                    uses parameters_redistribute;
                }    
                container rip {
                    presence "true";
                    configd:help "Redistribute RIPNG routes";
                    configd:end "/opt/vyatta/share/tmplscripts/protocols/ospf/redistribute/configd_end.sh";
                    uses parameters_redistribute;
                }    
                container connected {
                    presence "true";
                    configd:help "Redistribute connected routes";
                    configd:end "/opt/vyatta/share/tmplscripts/protocols/ospf/redistribute/configd_end.sh";
                    uses parameters_redistribute;
                }    
                container static {
                    presence "true";
                    configd:help "Redistribute static routes";
                    configd:end "/opt/vyatta/share/tmplscripts/protocols/ospf/redistribute/configd_end.sh";
                    uses parameters_redistribute;
                }    
            }
			container distance {
				presence "true";
				configd:help "Administrative distance";
				leaf global {
					type uint32 {
						range 1..255;
					}
					configd:help "OSPF administrative distance";
					configd:create "/opt/vyatta/share/tmplscripts/protocols/ospf/distance/global/configd_create.cli";
					configd:delete "/opt/vyatta/share/tmplscripts/protocols/ospf/distance/global/configd_delete.cli";
				}
				container ospf {
					presence "true";
					configd:help "OSPF administrative distance";
					configd:delete "/opt/vyatta/share/tmplscripts/protocols/ospf/distance/ospf/configd_delete.cli";
					leaf external {
						type uint32 {
							range 1..255;
						}
						configd:help "Distance for external routes";
						configd:create "/opt/vyatta/share/tmplscripts/protocols/ospf/distance/ospf/external/configd_create.cli";
						configd:delete "/opt/vyatta/share/tmplscripts/protocols/ospf/distance/ospf/external/configd_delete.cli";
					}
					leaf inter-area {
						type uint32 {
							range 1..255;
						}
						configd:help "Distance for inter-area routes";
						configd:create "/opt/vyatta/share/tmplscripts/protocols/ospf/distance/ospf/inter-area/configd_create.cli";
						configd:delete "/opt/vyatta/share/tmplscripts/protocols/ospf/distance/ospf/inter-area/configd_delete.cli";
					}
					leaf intra-area {
						type uint32 {
							range 1..255;
						}
						configd:help "Distance for intra-area routes";
						configd:create "/opt/vyatta/share/tmplscripts/protocols/ospf/distance/ospf/intra-area/configd_create.cli";
						configd:delete "/opt/vyatta/share/tmplscripts/protocols/ospf/distance/ospf/intra-area/configd_delete.cli";
					}
				}
			}
			list summary-address {
				configd:help "Summary network and mask";
				configd:create "/opt/vyatta/share/tmplscripts/protocols/ospf/summary-address/configd_create1.cli";
				configd:validate "/opt/vyatta/share/tmplscripts/protocols/ospf/summary-address/configd_validate.cli";
				key "tagnode";
				leaf tagnode {
					type types:ipv4-prefix;
					configd:help "Summary network and mask";
				}
				container advertise {
					presence "true";
					configd:help "Summary address to be advertised.";
					configd:create "/opt/vyatta/share/tmplscripts/protocols/ospf/summary-address/advertise/configd_create.sh";
					configd:delete "/opt/vyatta/share/tmplscripts/protocols/ospf/summary-address/advertise/configd_delete.sh";
					leaf tag {
						type uint32;
						configd:help "OSPF tag identifier for summary address.";
						configd:create "/opt/vyatta/share/tmplscripts/protocols/ospf/summary-address/advertise/tag/configd_create.sh";
						configd:delete "/opt/vyatta/share/tmplscripts/protocols/ospf/summary-address/advertise/tag/configd_delete.sh";
					}
				}
				leaf not-advertise {
					type empty;
					configd:help "Summary address which shouldn't be advertised.";
					configd:create "/opt/vyatta/share/tmplscripts/protocols/ospf/summary-address/not-advertise/configd_create.sh";
					configd:delete "/opt/vyatta/share/tmplscripts/protocols/ospf/summary-address/not-advertise/configd_delete.sh";
				}
			}
			container default-information {
				configd:help "Control distribution of default information";
				container originate {
					presence "true";
					configd:help "Distribute a default route";
					configd:end "/opt/vyatta/share/tmplscripts/protocols/ospf/default-information/originate/configd_end.sh";
					leaf metric-type {
						type enumeration {
							enum "1";
							enum "2";
						}
						configd:help "OSPF metric type for default routes";
					}
					leaf always {
						type empty;
						configd:help "Always advertise default route";
					}
					leaf route-map {
						type string;
						configd:help "Route map reference";
						configd:allowed "/opt/vyatta/share/tmplscripts/protocols/ospf/default-information/originate/route-map/configd_allowed.sh";
						configd:validate "/opt/vyatta/share/tmplscripts/protocols/ospf/default-information/originate/route-map/configd_validate.cli";
					}
					leaf metric {
						type uint32 {
							range 0..16777214;
						}
						configd:help "OSPF default metric";
					}
				}
			}
			list area {
				configd:help "OSPF Area";
				configd:validate "/opt/vyatta/share/tmplscripts/protocols/ospf/area/configd_validate.cli";
				key "tagnode";
				leaf tagnode {
					type union {
						type types:ipv4-address;
						type uint32;
					}
					configd:help "OSPF Area";
				}
				leaf authentication {
					type enumeration {
						enum "plaintext" {
							configd:help "Use plain-text authentication";
						}
						enum "md5" {
							configd:help "Use md5 authentication";
						}
					}
					configd:help "OSPF area authentication type";
					configd:allowed "/opt/vyatta/share/tmplscripts/protocols/ospf/area/authentication/configd_allowed.sh";
					configd:update "/opt/vyatta/share/tmplscripts/protocols/ospf/area/authentication/configd_update1.cli";
					configd:delete "/opt/vyatta/share/tmplscripts/protocols/ospf/area/authentication/configd_delete1.cli";
				}
				list virtual-link {
					configd:help "Virtual link";
					configd:create "/opt/vyatta/share/tmplscripts/protocols/ospf/area/virtual-link/configd_create1.cli";
					configd:delete "/opt/vyatta/share/tmplscripts/protocols/ospf/area/virtual-link/configd_delete1.cli";
					key "tagnode";
					leaf tagnode {
						type types:ipv4-address;
						configd:help "Virtual link";
					}
					container authentication {
						presence "true";
						configd:help "Authentication";
						leaf plaintext-password {
							type string {
								configd:syntax "/opt/vyatta/share/tmplscripts/protocols/ospf/area/virtual-link/authentication/plaintext-password/configd_syntax1.cli";
							}
							configd:secret "true";
							configd:help "Plain text password";
							configd:update "/opt/vyatta/share/tmplscripts/protocols/ospf/area/virtual-link/authentication/plaintext-password/configd_update.sh";
							configd:delete "/opt/vyatta/share/tmplscripts/protocols/ospf/area/virtual-link/authentication/plaintext-password/configd_delete.sh";
							configd:validate "/opt/vyatta/share/tmplscripts/protocols/ospf/area/virtual-link/authentication/plaintext-password/configd_validate1.cli";
						}
						leaf plaintext {
							type empty;
							configd:help "Plain text authentication";
							configd:update "/opt/vyatta/share/tmplscripts/protocols/ospf/area/virtual-link/authentication/plaintext/configd_update.sh";
							configd:delete "/opt/vyatta/share/tmplscripts/protocols/ospf/area/virtual-link/authentication/plaintext/configd_delete.sh";
							configd:validate "/opt/vyatta/share/tmplscripts/protocols/ospf/area/virtual-link/authentication/plaintext/configd_validate1.cli";
						}
						leaf md5 {
							type empty;
							configd:help "MD5 key id";
							configd:update "/opt/vyatta/share/tmplscripts/protocols/ospf/area/virtual-link/authentication/md5/configd_update.sh";
							configd:delete "/opt/vyatta/share/tmplscripts/protocols/ospf/area/virtual-link/authentication/md5/configd_delete.sh";
							configd:validate "/opt/vyatta/share/tmplscripts/protocols/ospf/area/virtual-link/authentication/md5/configd_validate1.cli";
						}
						list md5-key-id {
							configd:help "MD5 key id";
							configd:validate "/opt/vyatta/share/tmplscripts/protocols/ospf/area/virtual-link/authentication/md5-key-id/configd_validate1.cli";
							configd:create "/opt/vyatta/share/tmplscripts/protocols/ospf/area/virtual-link/authentication/md5-key-id/configd_create1.cli";
							configd:delete "/opt/vyatta/share/tmplscripts/protocols/ospf/area/virtual-link/authentication/md5-key-id/configd_delete1.cli";
							key "tagnode";
							leaf tagnode {
								type uint32 {
									range 1..255;
								}
								configd:help "MD5 key id";
							}
							leaf md5-key {
								type string {
									configd:syntax "/opt/vyatta/share/tmplscripts/protocols/ospf/area/virtual-link/authentication/md5-key-id/md5-key/configd_syntax1.cli";
								}
								configd:help "MD5 key";
							}
						}
					}
					leaf dead-interval {
						type uint32 {
							range 1..65535;
						}
						configd:help "Interval after which a neighbor is declared dead";
						default "40";
						configd:update "/opt/vyatta/share/tmplscripts/protocols/ospf/area/virtual-link/dead-interval/configd_update1.cli";
						configd:delete "/opt/vyatta/share/tmplscripts/protocols/ospf/area/virtual-link/dead-interval/configd_delete1.cli";
					}
					leaf hello-interval {
						type uint32 {
							range 1..65535;
						}
						configd:help "Interval between hello packets";
						default "10";
						configd:update "/opt/vyatta/share/tmplscripts/protocols/ospf/area/virtual-link/hello-interval/configd_update1.cli";
						configd:delete "/opt/vyatta/share/tmplscripts/protocols/ospf/area/virtual-link/hello-interval/configd_delete1.cli";
					}
					leaf retransmit-interval {
						type uint32 {
							range 1..65535;
						}
						configd:help "Interval between retransmitting lost link state advertisements";
						default "5";
						configd:update "/opt/vyatta/share/tmplscripts/protocols/ospf/area/virtual-link/retransmit-interval/configd_update1.cli";
						configd:delete "/opt/vyatta/share/tmplscripts/protocols/ospf/area/virtual-link/retransmit-interval/configd_delete1.cli";
					}
					leaf transmit-delay {
						type uint32 {
							range 1..65535;
						}
						configd:help "Link state transmit delay";
						default "1";
						configd:update "/opt/vyatta/share/tmplscripts/protocols/ospf/area/virtual-link/transmit-delay/configd_update1.cli";
						configd:delete "/opt/vyatta/share/tmplscripts/protocols/ospf/area/virtual-link/transmit-delay/configd_delete1.cli";
					}
				}
				container area-type {
					presence "true";
					configd:help "Area type";
					container stub {
						presence "true";
						configd:help "Stub OSPF area";
						configd:create "/opt/vyatta/share/tmplscripts/protocols/ospf/area/area-type/stub/configd_create.sh";
						configd:end "/opt/vyatta/share/tmplscripts/protocols/ospf/area/area-type/stub/configd_end.sh";
						leaf default-cost {
							type uint32 {
								range 0..16777214;
							}
							configd:help "Summary-default cost of stub area";
							configd:create "/opt/vyatta/share/tmplscripts/protocols/ospf/area/area-type/stub/default-cost/configd_create.sh";
							configd:update "/opt/vyatta/share/tmplscripts/protocols/ospf/area/area-type/stub/default-cost/configd_update.sh";
							configd:delete "/opt/vyatta/share/tmplscripts/protocols/ospf/area/area-type/stub/default-cost/configd_delete.sh";
						}
						leaf no-summary {
							type empty;
							configd:help "Do not inject inter-area routes into stub";
							configd:create "/opt/vyatta/share/tmplscripts/protocols/ospf/area/area-type/stub/no-summary/configd_create.sh";
						}
					}
					container nssa {
						presence "true";
						configd:help "Nssa OSPF area";
						configd:create "/opt/vyatta/share/tmplscripts/protocols/ospf/area/area-type/nssa/configd_create.sh";
						configd:delete "/opt/vyatta/share/tmplscripts/protocols/ospf/area/area-type/nssa/configd_delete.sh";
						leaf default-cost {
							type uint32 {
								range 0..16777214;
							}
							configd:help "Summary-default cost of nssa area";
							configd:create "/opt/vyatta/share/tmplscripts/protocols/ospf/area/area-type/nssa/default-cost/configd_create.sh";
							configd:update "/opt/vyatta/share/tmplscripts/protocols/ospf/area/area-type/nssa/default-cost/configd_update.sh";
							configd:delete "/opt/vyatta/share/tmplscripts/protocols/ospf/area/area-type/nssa/default-cost/configd_delete.sh";
						}
						container default-information-originate {
							presence "true";
							configd:help "Distribute a default route into an NSSA area";
							configd:end "/opt/vyatta/share/tmplscripts/protocols/ospf/area/area-type/nssa/default-information-originate/configd_end.sh";
							leaf metric-type {
								type enumeration {
									enum "1";
									enum "2";
								}
								configd:help "OSPF metric type for default routes";
							}
							leaf metric {
								type uint32 {
									range 0..16777214;
								}
								configd:help "OSPF default metric";
							}
							leaf route-map {
								type string;
								configd:help "Route map";
								configd:allowed "/opt/vyatta/share/tmplscripts/protocols/ospf/configd_route_map_allowed.sh";
								configd:validate "/opt/vyatta/share/tmplscripts/protocols/ospf/configd_route_map_validate.cli";
							}
						}
						leaf translate {
							type enumeration {
								enum "always" {
									configd:help "NSSA-ABR to always translate";
								}
								enum "candidate" {
									configd:help "NSSA-ABR for translate election (default)";
								}
								enum "never" {
									configd:help "NSSA-ABR do not translate";
								}
							}
							configd:help "Nssa-abr";
							configd:create "/opt/vyatta/share/tmplscripts/protocols/ospf/area/area-type/nssa/translate/configd_create.sh";
							configd:delete "/opt/vyatta/share/tmplscripts/protocols/ospf/area/area-type/nssa/translate/configd_delete.sh";
						}
						leaf no-summary {
							type empty;
							configd:help "Do not inject inter-area routes into stub";
							configd:create "/opt/vyatta/share/tmplscripts/protocols/ospf/area/area-type/nssa/no-summary/configd_create.sh";
							configd:delete "/opt/vyatta/share/tmplscripts/protocols/ospf/area/area-type/nssa/no-summary/configd_delete.sh";
						}
					}
				}
				leaf shortcut {
					type enumeration {
						enum "default" {
							configd:help "Set default; ";
						}
						enum "disable" {
							configd:help "Disable shortcutting mode; ";
						}
						enum "enable" {
							configd:help "Enable  shortcutting mode; ";
						}
					}
					configd:help "Area's shortcut mode";
					configd:allowed "/opt/vyatta/share/tmplscripts/protocols/ospf/area/shortcut/configd_allowed.sh";
					configd:update "/opt/vyatta/share/tmplscripts/protocols/ospf/area/shortcut/configd_update1.cli";
					configd:delete "/opt/vyatta/share/tmplscripts/protocols/ospf/area/shortcut/configd_delete1.cli";
				}
				list range {
					configd:help "Summarize routes matching prefix (border routers only)";
					configd:end "/opt/vyatta/share/tmplscripts/protocols/ospf/area/range/configd_end.sh";
					key "tagnode";
					leaf tagnode {
						type types:ipv4-prefix {
							configd:syntax "/opt/vyatta/share/tmplscripts/protocols/ospf/area/range/configd_syntax1.cli";
						}
						configd:help "Summarize routes matching prefix (border routers only)";
					}
					leaf not-advertise {
						type empty;
						configd:help "Do not advertise this range";
					}
				}
				leaf-list network {
					type types:ipv4-prefix {
						configd:syntax "/opt/vyatta/share/tmplscripts/protocols/ospf/area/network/configd_syntax1.cli";
					}
					ordered-by "user";
					configd:help "OSPF network [REQUIRED]";
					configd:create "/opt/vyatta/share/tmplscripts/protocols/ospf/area/network/configd_create.sh";
					configd:delete "/opt/vyatta/share/tmplscripts/protocols/ospf/area/network/configd_delete.sh";
				}
			}
			container auto-cost {
				presence "true";
				configd:help "Calculate OSPF interface cost according to bandwidth";
				leaf reference-bandwidth {
					type uint32 {
						range 1..4294967;
					}
					configd:help "Reference bandwidth method to assign OSPF cost";
					default "100";
					configd:update "/opt/vyatta/share/tmplscripts/protocols/ospf/auto-cost/reference-bandwidth/configd_update1.cli";
					configd:delete "/opt/vyatta/share/tmplscripts/protocols/ospf/auto-cost/reference-bandwidth/configd_delete1.cli";
				}
			}
			container overflow {
				configd:help "Configure OSPF Overflow handling capabilities.";
				container database {
					configd:help "configure type of ospf overflow protection";
					container hard {
						configd:help "Hard limit on number of LSAs, instance will shut down if limit exceeded";
						leaf limit {
							type uint32 {
								range 0..4294967294;
							}
							configd:help "Max LSAs in database.";
							configd:update "/opt/vyatta/share/tmplscripts/protocols/ospf/overflow/database/hard/limit/configd_update.sh";
							configd:delete "/opt/vyatta/share/tmplscripts/protocols/ospf/overflow/database/hard/limit/configd_delete.sh";
							configd:validate "/opt/vyatta/share/tmplscripts/protocols/ospf/overflow/database/hard/limit/configd_validate1.cli";
						}
					}
					container external {
						presence "true";
						configd:help "Max AS-External LSAs in database.";
						configd:validate "/opt/vyatta/share/tmplscripts/protocols/ospf/overflow/database/external/configd_validate1.cli";
						list limit {
							configd:help "Max LSAs in database.";
							configd:validate "/opt/vyatta/share/tmplscripts/protocols/ospf/overflow/database/external/limit/configd_validate1.cli";
							key "tagnode";
							leaf tagnode {
								type uint32 {
									range 0..2147483647;
								}
								configd:help "Max LSAs in database.";
							}
							leaf recovery {
								type uint32 {
									range 0..65535;
								}
								configd:help "Time to recover (0 implies no recovery)";
								default "0";
								configd:update "/opt/vyatta/share/tmplscripts/protocols/ospf/overflow/database/external/limit/recovery/configd_update.sh";
								configd:delete "/opt/vyatta/share/tmplscripts/protocols/ospf/overflow/database/external/limit/recovery/configd_delete.sh";
							}
						}
					}
					container soft {
						configd:help "Soft limit on number of LSAs in database, will warn if exceeded";
						leaf limit {
							type uint32 {
								range 0..4294967294;
							}
							configd:help "Max LSAs in database.";
							configd:update "/opt/vyatta/share/tmplscripts/protocols/ospf/overflow/database/soft/limit/configd_update.sh";
							configd:delete "/opt/vyatta/share/tmplscripts/protocols/ospf/overflow/database/soft/limit/configd_delete.sh";
							configd:validate "/opt/vyatta/share/tmplscripts/protocols/ospf/overflow/database/soft/limit/configd_validate1.cli";
						}
					}
				}
			}
			container log {
				configd:help "OSPF logging parameters";
				leaf all {
					type empty;
					configd:help "Enable all OSPF logs";
					configd:create "/opt/vyatta/share/tmplscripts/protocols/ospf/log/configd_create.sh";
					configd:delete "/opt/vyatta/share/tmplscripts/protocols/ospf/log/configd_delete.pl $VAR(@)";
				}
				container rib {
					configd:help "OSPF rib logs";
					leaf all {
						type empty;
						configd:help "Enable OSPF rib all logs";
						configd:create "/opt/vyatta/share/tmplscripts/protocols/ospf/log/rib/configd_create.sh";
						configd:delete "/opt/vyatta/share/tmplscripts/protocols/ospf/log/configd_delete.pl $VAR(../@) $VAR(@)";
					}
					leaf interface {
						type empty;
						configd:help "Enable OSPF rib interface logs";
						configd:create "/opt/vyatta/share/tmplscripts/protocols/ospf/log/rib/configd_create.sh";
						configd:delete "/opt/vyatta/share/tmplscripts/protocols/ospf/log/configd_delete.pl $VAR(../@) $VAR(@)";
					}
					leaf redistribute {
						type empty;
						configd:help "Enable OSPF rib redistribute logs";
						configd:create "/opt/vyatta/share/tmplscripts/protocols/ospf/log/rib/configd_create.sh";
						configd:delete "/opt/vyatta/share/tmplscripts/protocols/ospf/log/configd_delete.pl $VAR(../@) $VAR(@)";
					}
				}
				container nsm {
					configd:help "OSPF nsm logs";
					leaf all {
						type empty;
						configd:help "Enable OSPF nsm all logs";
						configd:create "/opt/vyatta/share/tmplscripts/protocols/ospf/log/nsm/configd_create.sh";
						configd:delete "/opt/vyatta/share/tmplscripts/protocols/ospf/log/configd_delete.pl $VAR(../@) $VAR(@)";
					}
					leaf interface {
						type empty;
						configd:help "Enable OSPF nsm interface logs";
						configd:create "/opt/vyatta/share/tmplscripts/protocols/ospf/log/nsm/configd_create.sh";
						configd:delete "/opt/vyatta/share/tmplscripts/protocols/ospf/log/configd_delete.pl $VAR(../@) $VAR(@)";
					}
					leaf redistribute {
						type empty;
						configd:help "Enable OSPF nsm redistribute logs";
						configd:create "/opt/vyatta/share/tmplscripts/protocols/ospf/log/nsm/configd_create.sh";
						configd:delete "/opt/vyatta/share/tmplscripts/protocols/ospf/log/configd_delete.pl $VAR(../@) $VAR(@)";
					}
				}
				container events {
					configd:help "OSPF event logs";
					leaf all {
						type empty;
						configd:help "Enable OSPF events all logs";
						configd:create "/opt/vyatta/share/tmplscripts/protocols/ospf/log/events/configd_create.sh";
						configd:delete "/opt/vyatta/share/tmplscripts/protocols/ospf/log/configd_delete.pl $VAR(../@) $VAR(@)";
					}
					leaf abr {
						type empty;
						configd:help "Enable OSPF events abr logs";
						configd:create "/opt/vyatta/share/tmplscripts/protocols/ospf/log/events/configd_create.sh";
						configd:delete "/opt/vyatta/share/tmplscripts/protocols/ospf/log/configd_delete.pl $VAR(../@) $VAR(@)";
					}
					leaf asbr {
						type empty;
						configd:help "Enable OSPF events asbr logs";
						configd:create "/opt/vyatta/share/tmplscripts/protocols/ospf/log/events/configd_create.sh";
						configd:delete "/opt/vyatta/share/tmplscripts/protocols/ospf/log/configd_delete.pl $VAR(../@) $VAR(@)";
					}
					leaf lsa {
						type empty;
						configd:help "Enable OSPF events lsa logs";
						configd:create "/opt/vyatta/share/tmplscripts/protocols/ospf/log/events/configd_create.sh";
						configd:delete "/opt/vyatta/share/tmplscripts/protocols/ospf/log/configd_delete.pl $VAR(../@) $VAR(@)";
					}
					leaf nssa {
						type empty;
						configd:help "Enable OSPF events nssa logs";
						configd:create "/opt/vyatta/share/tmplscripts/protocols/ospf/log/events/configd_create.sh";
						configd:delete "/opt/vyatta/share/tmplscripts/protocols/ospf/log/configd_delete.pl $VAR(../@) $VAR(@)";
					}
					leaf os {
						type empty;
						configd:help "Enable OSPF events os logs";
						configd:create "/opt/vyatta/share/tmplscripts/protocols/ospf/log/events/configd_create.sh";
						configd:delete "/opt/vyatta/share/tmplscripts/protocols/ospf/log/configd_delete.pl $VAR(../@) $VAR(@)";
					}
					leaf router {
						type empty;
						configd:help "Enable OSPF events router logs";
						configd:create "/opt/vyatta/share/tmplscripts/protocols/ospf/log/events/configd_create.sh";
						configd:delete "/opt/vyatta/share/tmplscripts/protocols/ospf/log/configd_delete.pl $VAR(../@) $VAR(@)";
					}
					leaf vlink {
						type empty;
						configd:help "Enable OSPF events vlink logs";
						configd:create "/opt/vyatta/share/tmplscripts/protocols/ospf/log/events/configd_create.sh";
						configd:delete "/opt/vyatta/share/tmplscripts/protocols/ospf/log/configd_delete.pl $VAR(../@) $VAR(@)";
					}
				}
				container ifsm {
					configd:help "OSPF ifsm logs";
					leaf all {
						type empty;
						configd:help "Enable OSPF ifsm all logs";
						configd:create "/opt/vyatta/share/tmplscripts/protocols/ospf/log/ifsm/configd_create.sh";
						configd:delete "/opt/vyatta/share/tmplscripts/protocols/ospf/log/configd_delete.pl $VAR(../@) $VAR(@)";
					}
					leaf events {
						type empty;
						configd:help "Enable OSPF ifsm events logs";
						configd:create "/opt/vyatta/share/tmplscripts/protocols/ospf/log/ifsm/configd_create.sh";
						configd:delete "/opt/vyatta/share/tmplscripts/protocols/ospf/log/configd_delete.pl $VAR(../@) $VAR(@)";
					}
					leaf status {
						type empty;
						configd:help "Enable OSPF ifsm status logs";
						configd:create "/opt/vyatta/share/tmplscripts/protocols/ospf/log/ifsm/configd_create.sh";
						configd:delete "/opt/vyatta/share/tmplscripts/protocols/ospf/log/configd_delete.pl $VAR(../@) $VAR(@)";
					}
					leaf timers {
						type empty;
						configd:help "Enable OSPF ifsm timers logs";
						configd:create "/opt/vyatta/share/tmplscripts/protocols/ospf/log/ifsm/configd_create.sh";
						configd:delete "/opt/vyatta/share/tmplscripts/protocols/ospf/log/configd_delete.pl $VAR(../@) $VAR(@)";
					}
				}
				container lsa {
					configd:help "OSPF lsa logs";
					leaf all {
						type empty;
						configd:help "Enable OSPF lsa all logs";
						configd:create "/opt/vyatta/share/tmplscripts/protocols/ospf/log/lsa/configd_create.sh";
						configd:delete "/opt/vyatta/share/tmplscripts/protocols/ospf/log/configd_delete.pl $VAR(../@) $VAR(@)";
					}
					leaf flooding {
						type empty;
						configd:help "Enable OSPF lsa flooding logs";
						configd:create "/opt/vyatta/share/tmplscripts/protocols/ospf/log/lsa/configd_create.sh";
						configd:delete "/opt/vyatta/share/tmplscripts/protocols/ospf/log/configd_delete.pl $VAR(../@) $VAR(@)";
					}
					leaf generate {
						type empty;
						configd:help "Enable OSPF lsa generate logs";
						configd:create "/opt/vyatta/share/tmplscripts/protocols/ospf/log/lsa/configd_create.sh";
						configd:delete "/opt/vyatta/share/tmplscripts/protocols/ospf/log/configd_delete.pl $VAR(../@) $VAR(@)";
					}
					leaf install {
						type empty;
						configd:help "Enable OSPF lsa install logs";
						configd:create "/opt/vyatta/share/tmplscripts/protocols/ospf/log/lsa/configd_create.sh";
						configd:delete "/opt/vyatta/share/tmplscripts/protocols/ospf/log/configd_delete.pl $VAR(../@) $VAR(@)";
					}
					leaf maxage {
						type empty;
						configd:help "Enable OSPF lsa maxage logs";
						configd:create "/opt/vyatta/share/tmplscripts/protocols/ospf/log/lsa/configd_create.sh";
						configd:delete "/opt/vyatta/share/tmplscripts/protocols/ospf/log/configd_delete.pl $VAR(../@) $VAR(@)";
					}
					leaf refresh {
						type empty;
						configd:help "Enable OSPF lsa refresh logs";
						configd:create "/opt/vyatta/share/tmplscripts/protocols/ospf/log/lsa/configd_create.sh";
						configd:delete "/opt/vyatta/share/tmplscripts/protocols/ospf/log/configd_delete.pl $VAR(../@) $VAR(@)";
					}
				}
				container nfsm {
					configd:help "OSPF nfsm logs";
					leaf all {
						type empty;
						configd:help "Enable OSPF nfsm all logs";
						configd:create "/opt/vyatta/share/tmplscripts/protocols/ospf/log/nfsm/configd_create.sh";
						configd:delete "/opt/vyatta/share/tmplscripts/protocols/ospf/log/configd_delete.pl $VAR(../@) $VAR(@)";
					}
					leaf events {
						type empty;
						configd:help "Enable OSPF nfsm events logs";
						configd:create "/opt/vyatta/share/tmplscripts/protocols/ospf/log/nfsm/configd_create.sh";
						configd:delete "/opt/vyatta/share/tmplscripts/protocols/ospf/log/configd_delete.pl $VAR(../@) $VAR(@)";
					}
					leaf status {
						type empty;
						configd:help "Enable OSPF nfsm status logs";
						configd:create "/opt/vyatta/share/tmplscripts/protocols/ospf/log/nfsm/configd_create.sh";
						configd:delete "/opt/vyatta/share/tmplscripts/protocols/ospf/log/configd_delete.pl $VAR(../@) $VAR(@)";
					}
					leaf timers {
						type empty;
						configd:help "Enable OSPF nfsm timers logs";
						configd:create "/opt/vyatta/share/tmplscripts/protocols/ospf/log/nfsm/configd_create.sh";
						configd:delete "/opt/vyatta/share/tmplscripts/protocols/ospf/log/configd_delete.pl $VAR(../@) $VAR(@)";
					}
				}
				container route {
					configd:help "OSPF route logs";
					leaf all {
						type empty;
						configd:help "Enable OSPF route all logs";
						configd:create "/opt/vyatta/share/tmplscripts/protocols/ospf/log/route/configd_create.sh";
						configd:delete "/opt/vyatta/share/tmplscripts/protocols/ospf/log/configd_delete.pl $VAR(../@) $VAR(@)";
					}
					leaf ase {
						type empty;
						configd:help "Enable OSPF route ase logs";
						configd:create "/opt/vyatta/share/tmplscripts/protocols/ospf/log/route/configd_create.sh";
						configd:delete "/opt/vyatta/share/tmplscripts/protocols/ospf/log/configd_delete.pl $VAR(../@) $VAR(@)";
					}
					leaf ia {
						type empty;
						configd:help "Enable OSPF route ia logs";
						configd:create "/opt/vyatta/share/tmplscripts/protocols/ospf/log/route/configd_create.sh";
						configd:delete "/opt/vyatta/share/tmplscripts/protocols/ospf/log/configd_delete.pl $VAR(../@) $VAR(@)";
					}
					leaf install {
						type empty;
						configd:help "Enable OSPF route install logs";
						configd:create "/opt/vyatta/share/tmplscripts/protocols/ospf/log/route/configd_create.sh";
						configd:delete "/opt/vyatta/share/tmplscripts/protocols/ospf/log/configd_delete.pl $VAR(../@) $VAR(@)";
					}
					leaf spf {
						type empty;
						configd:help "Enable OSPF route spf logs";
						configd:create "/opt/vyatta/share/tmplscripts/protocols/ospf/log/route/configd_create.sh";
						configd:delete "/opt/vyatta/share/tmplscripts/protocols/ospf/log/configd_delete.pl $VAR(../@) $VAR(@)";
					}
				}
				container packet {
					configd:help "OSPF packet logs";
					leaf all {
						type empty;
						configd:help "Enable OSPF packet all logs";
						configd:create "/opt/vyatta/share/tmplscripts/protocols/ospf/log/packet/configd_create.sh";
						configd:delete "/opt/vyatta/share/tmplscripts/protocols/ospf/log/configd_delete.pl $VAR(../@) $VAR(@)";
					}
					leaf dd {
						type empty;
						configd:help "Enable OSPF packet dd logs";
						configd:create "/opt/vyatta/share/tmplscripts/protocols/ospf/log/packet/configd_create.sh";
						configd:delete "/opt/vyatta/share/tmplscripts/protocols/ospf/log/configd_delete.pl $VAR(../@) $VAR(@)";
					}
					leaf detail {
						type empty;
						configd:help "Enable OSPF packet detail logs";
						configd:create "/opt/vyatta/share/tmplscripts/protocols/ospf/log/packet/configd_create.sh";
						configd:delete "/opt/vyatta/share/tmplscripts/protocols/ospf/log/configd_delete.pl $VAR(../@) $VAR(@)";
					}
					leaf hello {
						type empty;
						configd:help "Enable OSPF packet hello logs";
						configd:create "/opt/vyatta/share/tmplscripts/protocols/ospf/log/packet/configd_create.sh";
						configd:delete "/opt/vyatta/share/tmplscripts/protocols/ospf/log/configd_delete.pl $VAR(../@) $VAR(@)";
					}
					leaf ls-ack {
						type empty;
						configd:help "Enable OSPF packet ls-ack logs";
						configd:create "/opt/vyatta/share/tmplscripts/protocols/ospf/log/packet/configd_create.sh";
						configd:delete "/opt/vyatta/share/tmplscripts/protocols/ospf/log/configd_delete.pl $VAR(../@) $VAR(@)";
					}
					leaf ls-request {
						type empty;
						configd:help "Enable OSPF packet ls-request logs";
						configd:create "/opt/vyatta/share/tmplscripts/protocols/ospf/log/packet/configd_create.sh";
						configd:delete "/opt/vyatta/share/tmplscripts/protocols/ospf/log/configd_delete.pl $VAR(../@) $VAR(@)";
					}
					leaf ls-update {
						type empty;
						configd:help "Enable OSPF packet ls-update logs";
						configd:create "/opt/vyatta/share/tmplscripts/protocols/ospf/log/packet/configd_create.sh";
						configd:delete "/opt/vyatta/share/tmplscripts/protocols/ospf/log/configd_delete.pl $VAR(../@) $VAR(@)";
					}
					leaf send {
						type empty;
						configd:help "Enable OSPF packet send logs";
						configd:create "/opt/vyatta/share/tmplscripts/protocols/ospf/log/packet/configd_create.sh";
						configd:delete "/opt/vyatta/share/tmplscripts/protocols/ospf/log/configd_delete.pl $VAR(../@) $VAR(@)";
					}
					leaf recv {
						type empty;
						configd:help "Enable OSPF packet recv logs";
						configd:create "/opt/vyatta/share/tmplscripts/protocols/ospf/log/packet/configd_create.sh";
						configd:delete "/opt/vyatta/share/tmplscripts/protocols/ospf/log/configd_delete.pl $VAR(../@) $VAR(@)";
					}
				}
			}
		}
	}


	grouping itf-ip-ospf {
		container ospf {
			configd:help "Open Shortest Path First (OSPF) parameters";
			presence "true";
			leaf priority {
				type uint32 {
					range 0..255;
				}
				configd:help "Router priority";
				default "1";
				configd:update "/opt/vyatta/share/tmplscripts/interfaces/all/ip/ospf/priority/configd_update.sh";
				configd:delete "/opt/vyatta/share/tmplscripts/interfaces/all/ip/ospf/priority/configd_delete.sh";
			}
			container authentication {
				presence "true";
				configd:help "OSPF interface authentication";
				leaf plaintext-password {
					type string {
						pattern '[^\t\n\r ]{1,8}' {
							error-message "Password must be 8 characters or less";
						}
					}
					configd:secret "true";
					configd:help "Plain text password";
					configd:update "/opt/vyatta/share/tmplscripts/interfaces/all/ip/ospf/authentication/plaintext-password/configd_update.sh";
					configd:delete "/opt/vyatta/share/tmplscripts/interfaces/all/ip/ospf/authentication/plaintext-password/configd_delete.sh";
				}
				leaf plaintext {
					type empty;
					configd:help "Enable/disable plain text authentication";
					configd:update "/opt/vyatta/share/tmplscripts/interfaces/all/ip/ospf/authentication/plaintext/configd_update.sh";
					configd:delete "/opt/vyatta/share/tmplscripts/interfaces/all/ip/ospf/authentication/plaintext/configd_delete.sh";
				}
				leaf md5 {
					type empty;
					configd:help "MD5 parameters";
					configd:create "/opt/vyatta/share/tmplscripts/interfaces/all/ip/ospf/authentication/md5/configd_create.sh";
					configd:delete "/opt/vyatta/share/tmplscripts/interfaces/all/ip/ospf/authentication/md5/configd_delete.sh";
				}
				list md5-key-id {
					configd:help "MD5 key id";
					configd:validate "/opt/vyatta/share/tmplscripts/interfaces/all/ip/ospf/authentication/md5-key-id/configd_validate1.cli";
					key "tagnode";
					leaf tagnode {
						type uint32 {
							range 1..255;
						}
						configd:help "MD5 key id";
					}
					leaf md5-key {
						type string {
							pattern '[^\t\n\r ]{1,16}' {
								error-message "MD5 key must be 16 characters or less";
							}
						}
						configd:help "MD5 key";
						configd:create "/opt/vyatta/share/tmplscripts/interfaces/all/ip/ospf/authentication/md5-key-id/md5-key/configd_create.sh";
						configd:update "/opt/vyatta/share/tmplscripts/interfaces/all/ip/ospf/authentication/md5-key-id/md5-key/configd_update.sh";
						configd:delete "/opt/vyatta/share/tmplscripts/interfaces/all/ip/ospf/authentication/md5-key-id/md5-key/configd_delete.sh";
					}
				}
			}
			leaf mtu-ignore {
				type empty;
				configd:help "Disable Maximum Transmission Unit (MTU) mismatch detection";
				configd:create "/opt/vyatta/share/tmplscripts/interfaces/all/ip/ospf/mtu-ignore/configd_create.sh";
				configd:delete "/opt/vyatta/share/tmplscripts/interfaces/all/ip/ospf/mtu-ignore/configd_delete.sh";
			}
			leaf dead-interval {
				type uint32 {
					range 1..65535;
				}
				configd:help "Interval after which neighbor is dead";
				default "40";
				configd:update "/opt/vyatta/share/tmplscripts/interfaces/all/ip/ospf/dead-interval/configd_update.sh";
				configd:delete "/opt/vyatta/share/tmplscripts/interfaces/all/ip/ospf/dead-interval/configd_delete.sh";
			}
			leaf hello-interval {
				type uint32 {
					range 1..65535;
				}
				configd:help "Interval between hello packets";
				configd:create "/opt/vyatta/share/tmplscripts/interfaces/all/ip/ospf/hello-interval/configd_create.sh";
				configd:delete "/opt/vyatta/share/tmplscripts/interfaces/all/ip/ospf/hello-interval/configd_delete.sh";
			}
			leaf retransmit-interval {
				type uint32 {
					range 5..65535;
				}
				configd:help "Interval between retransmitting lost link state advertisements";
				default "5";
				configd:update "/opt/vyatta/share/tmplscripts/interfaces/all/ip/ospf/retransmit-interval/configd_update.sh";
				configd:delete "/opt/vyatta/share/tmplscripts/interfaces/all/ip/ospf/retransmit-interval/configd_delete.sh";
			}
			leaf cost {
				type uint32 {
					range 1..65535;
				}
				configd:help "Interface cost";
				configd:update "/opt/vyatta/share/tmplscripts/interfaces/all/ip/ospf/cost/configd_update.sh";
				configd:delete "/opt/vyatta/share/tmplscripts/interfaces/all/ip/ospf/cost/configd_delete.sh";
			}
			leaf network {
				type enumeration {
					enum "broadcast" {
						configd:help "Broadcast network type";
					}
					enum "non-broadcast" {
						configd:help "Non-broadcast network type";
					}
					enum "point-to-multipoint" {
						configd:help "Point-to-multipoint network type";
					}
					enum "point-to-point" {
						configd:help "Point-to-point network type";
					}
				}
				configd:help "Network type";
				configd:update "/opt/vyatta/share/tmplscripts/interfaces/all/ip/ospf/network/configd_update.sh";
				configd:delete "/opt/vyatta/share/tmplscripts/interfaces/all/ip/ospf/network/configd_delete.sh";
				configd:validate "/opt/vyatta/share/tmplscripts/interfaces/all/ip/ospf/network/configd_validate.sh";
			}
			leaf transmit-delay {
				type uint32 {
					range 1..65535;
				}
				configd:help "Link state transmit delay";
				default "1";
				configd:update "/opt/vyatta/share/tmplscripts/interfaces/all/ip/ospf/transmit-delay/configd_update.sh";
				configd:delete "/opt/vyatta/share/tmplscripts/interfaces/all/ip/ospf/transmit-delay/configd_delete.sh";
			}
		}
	}

    /* Augmenting trap notifications */
    augment /service:service/service-snmp:snmp/service-snmp:notification {
        container ospf {
            configd:help "OSPF Notifications";
            leaf all {
                type empty;
                configd:help "OSPF Notifications";
                configd:create "vtysh -c \"configure terminal\" -c \"ospf notification all\"";
                configd:delete "vtysh -c \"configure terminal\" -c \"no ospf notification\"";
            }
        }
    }

	augment /if:interfaces/interfaces-bridge:bridge/interfaces-bridge:ip {
		uses itf-ip-ospf;
	}
	augment /if:interfaces/interfaces-dataplane:dataplane/interfaces-dataplane:ip {
		uses itf-ip-ospf {
			refine ospf {
				configd:validate "/opt/vyatta/share/tmplscripts/interfaces/dataplane/ip/configd_validate.sh";
			}
		}

	}
	augment /if:interfaces/interfaces-dataplane:dataplane/interfaces-dataplane:vif/interfaces-dataplane:ip {
		uses itf-ip-ospf {
			refine ospf {
				configd:validate "/opt/vyatta/share/tmplscripts/interfaces/dataplane/vif/ip/configd_validate.sh";
			}
		}
	}
	augment /if:interfaces/interfaces-l2tpeth:l2tpeth/interfaces-l2tpeth:ip {
		uses itf-ip-ospf;
	}
	augment /if:interfaces/interfaces-l2tpeth:l2tpeth/interfaces-l2tpeth:vif/interfaces-l2tpeth:ip {
		uses itf-ip-ospf;
	}
	augment /if:interfaces/interfaces-loopback:loopback/interfaces-loopback:ip {
		uses itf-ip-ospf {
			refine ospf/authentication/md5-key-id/md5-key {
				configd:secret "true";
			}
		}
	}
	augment /if:interfaces/interfaces-openvpn:openvpn/interfaces-openvpn:ip {
		uses itf-ip-ospf;
	}
	augment /if:interfaces/interfaces-tunnel:tunnel/interfaces-tunnel:ip {
		uses itf-ip-ospf;
	}
	augment /if:interfaces/interfaces-vti:vti/interfaces-vti:ip {
		uses itf-ip-ospf;
	}
	augment /if:interfaces/interfaces-bonding:bonding/interfaces-bonding:ip {
		uses itf-ip-ospf {
			refine ospf {
				configd:validate "/opt/vyatta/share/tmplscripts/interfaces/dataplane/ip/configd_validate.sh";
			}
		}
	}
	augment /if:interfaces/interfaces-bonding:bonding/interfaces-bonding:vif/interfaces-bonding:ip {
		uses itf-ip-ospf {
			refine ospf {
				configd:validate "/opt/vyatta/share/tmplscripts/interfaces/dataplane/ip/configd_validate.sh";
			}
		}
	}
}
