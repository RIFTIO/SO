module vyatta-interfaces-vhost-policy-v1 {
	namespace "urn:vyatta.com:mgmt:vyatta-interfaces-vhost-policy:1";
	prefix vyatta-interfaces-vhost-policy-v1;

	import vyatta-interfaces-v1 {
		prefix if;
	}
	import vyatta-policy-v1 {
		prefix policy;
	}
	import vyatta-interfaces-vhost-v1 {
		prefix interfaces-vhost;
	}
	import vyatta-interfaces-vhost-vif-v1 {
		prefix vif;
	}

	organization "Brocade Communications Systems, Inc.";
	contact
		"Brocade Communications Systems, Inc.
                 Postal: 130 Holger Way
                         San Jose, CA 95134
                 E-mail: support@Brocade.com
                 Web: www.brocade.com";

	revision 2015-09-29 {
		description "Initial revision";
	}


	augment /if:interfaces/interfaces-vhost:vhost {
		uses policy:policy-binding;
	}

	augment /if:interfaces/interfaces-vhost:vhost/vif:vif {
		uses policy:policy-binding;
	}
}
