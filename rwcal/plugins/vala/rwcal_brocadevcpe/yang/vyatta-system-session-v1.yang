module vyatta-system-session-v1 {
	namespace "urn:vyatta.com:mgmt:vyatta-system-session:1";
	prefix vyatta-system-session-v1;

	import vyatta-system-v1 {
		prefix system;
	}
	import configd-v1 {
		prefix configd;
	}

	organization "Brocade Communications Systems, Inc.";
	contact
		"Brocade Communications Systems, Inc.
		 Postal: 130 Holger Way
		         San Jose, CA 95134
		 E-mail: support@Brocade.com
		 Web: www.brocade.com";

	revision 2015-08-06 {
		description "Initial revision.";
	}

	augment /system:system {
		container session {
			presence "true";
			configd:help "Configure timeouts for session";
			leaf table-size {
				type uint32 {
					range 1..100000000 {
						error-message "Value must be between 1 and 100000000";
					}
				}
				configd:help "Size of connection tracking table";
				default "1048576";
				configd:update "/opt/vyatta/share/tmplscripts/system/session/table-size/configd_update.sh";
			}
			container timeout {
				presence "true";
				configd:help "Connection timeout options";
				container tcp {
					presence "true";
					configd:help "TCP connection timeout options";
					leaf close-wait {
						type uint32 {
							range 1..21474836 {
								error-message "Value must be between 1 and 21474836";
							}
						}
						configd:help "TCP CLOSE-WAIT timeout in seconds";
						configd:delete "/opt/vyatta/share/tmplscripts/system/session/timeout/tcp/close-wait/configd_delete.sh";
						configd:update "/opt/vyatta/share/tmplscripts/system/session/timeout/tcp/close-wait/configd_update.sh";
					}
					leaf established {
						type uint32 {
							range 1..21474836 {
								error-message "Value must be between 1 and 21474836";
							}
						}
						configd:help "TCP ESTABLISHED timeout in seconds";
						configd:delete "/opt/vyatta/share/tmplscripts/system/session/timeout/tcp/established/configd_delete.sh";
						configd:update "/opt/vyatta/share/tmplscripts/system/session/timeout/tcp/established/configd_update.sh";
					}
					leaf syn-sent {
						type uint32 {
							range 1..21474836 {
								error-message "Value must be between 1 and 21474836";
							}
						}
						configd:help "TCP SYN-SENT timeout in seconds";
						configd:delete "/opt/vyatta/share/tmplscripts/system/session/timeout/tcp/syn-sent/configd_delete.sh";
						configd:update "/opt/vyatta/share/tmplscripts/system/session/timeout/tcp/syn-sent/configd_update.sh";
					}
					leaf fin-received {
						type uint32 {
							range 1..21474836 {
								error-message "Value must be between 1 and 21474836";
							}
						}
						configd:help "TCP FIN-RECEIVED timeout in seconds";
						configd:delete "/opt/vyatta/share/tmplscripts/system/session/timeout/tcp/fin-received/configd_delete.sh";
						configd:update "/opt/vyatta/share/tmplscripts/system/session/timeout/tcp/fin-received/configd_update.sh";
					}
					leaf fin-sent {
						type uint32 {
							range 1..21474836 {
								error-message "Value must be between 1 and 21474836";
							}
						}
						configd:help "TCP FIN-SENT timeout in seconds";
						configd:delete "/opt/vyatta/share/tmplscripts/system/session/timeout/tcp/fin-sent/configd_delete.sh";
						configd:update "/opt/vyatta/share/tmplscripts/system/session/timeout/tcp/fin-sent/configd_update.sh";
					}
					leaf closing {
						type uint32 {
							range 1..21474836 {
								error-message "Value must be between 1 and 21474836";
							}
						}
						configd:help "TCP CLOSING timeout in seconds";
						configd:delete "/opt/vyatta/share/tmplscripts/system/session/timeout/tcp/closing/configd_delete.sh";
						configd:update "/opt/vyatta/share/tmplscripts/system/session/timeout/tcp/closing/configd_update.sh";
					}
					leaf simsyn-sent {
						type uint32 {
							range 1..21474836 {
								error-message "Value must be between 1 and 21474836";
							}
						}
						configd:help "TCP SIMSYN-SENT timeout in seconds";
						configd:delete "/opt/vyatta/share/tmplscripts/system/session/timeout/tcp/simsyn-sent/configd_delete.sh";
						configd:update "/opt/vyatta/share/tmplscripts/system/session/timeout/tcp/simsyn-sent/configd_update.sh";
					}
					leaf time-wait {
						type uint32 {
							range 1..21474836 {
								error-message "Value must be between 1 and 21474836";
							}
						}
						configd:help "TCP TIME-WAIT timeout in seconds";
						configd:delete "/opt/vyatta/share/tmplscripts/system/session/timeout/tcp/time-wait/configd_delete.sh";
						configd:update "/opt/vyatta/share/tmplscripts/system/session/timeout/tcp/time-wait/configd_update.sh";
					}
					leaf last-ack {
						type uint32 {
							range 1..21474836 {
								error-message "Value must be between 1 and 21474836";
							}
						}
						configd:help "TCP LAST-ACK timeout in seconds";
						configd:delete "/opt/vyatta/share/tmplscripts/system/session/timeout/tcp/last-ack/configd_delete.sh";
						configd:update "/opt/vyatta/share/tmplscripts/system/session/timeout/tcp/last-ack/configd_update.sh";
					}
					leaf syn-received {
						type uint32 {
							range 1..21474836 {
								error-message "Value must be between 1 and 21474836";
							}
						}
						configd:help "TCP SYN-RECEIVED timeout in seconds";
						configd:delete "/opt/vyatta/share/tmplscripts/system/session/timeout/tcp/syn-received/configd_delete.sh";
						configd:update "/opt/vyatta/share/tmplscripts/system/session/timeout/tcp/syn-received/configd_update.sh";
					}
					leaf closed {
						type uint32 {
							range 1..21474836 {
								error-message "Value must be between 1 and 21474836";
							}
						}
						configd:help "TCP CLOSED timeout in seconds";
						configd:delete "/opt/vyatta/share/tmplscripts/system/session/timeout/tcp/closed/configd_delete.sh";
						configd:update "/opt/vyatta/share/tmplscripts/system/session/timeout/tcp/closed/configd_update.sh";
					}
					leaf fin-wait {
						type uint32 {
							range 1..21474836 {
								error-message "Value must be between 1 and 21474836";
							}
						}
						configd:help "TCP FIN-WAIT timeout in seconds";
						configd:delete "/opt/vyatta/share/tmplscripts/system/session/timeout/tcp/fin-wait/configd_delete.sh";
						configd:update "/opt/vyatta/share/tmplscripts/system/session/timeout/tcp/fin-wait/configd_update.sh";
					}
				}
				container icmp {
					presence "true";
					configd:help "ICMP timeout";
					leaf established {
						type uint32 {
							range 1..21474836 {
								error-message "Value must be between 1 and 21474836";
							}
						}
						configd:help "ICMP ESTABLISHED timeout in seconds";
						configd:delete "/opt/vyatta/share/tmplscripts/system/session/timeout/icmp/established/configd_delete.sh";
						configd:update "/opt/vyatta/share/tmplscripts/system/session/timeout/icmp/established/configd_update.sh";
					}
					leaf new {
						type uint32 {
							range 1..21474836 {
								error-message "Value must be between 1 and 21474836";
							}
						}
						configd:help "ICMP NEW timeout in seconds";
						configd:delete "/opt/vyatta/share/tmplscripts/system/session/timeout/icmp/new/configd_delete.sh";
						configd:update "/opt/vyatta/share/tmplscripts/system/session/timeout/icmp/new/configd_update.sh";
					}
				}
				container other {
					presence "true";
					configd:help "Generic connection timeout";
					leaf established {
						type uint32 {
							range 1..21474836 {
								error-message "Value must be between 1 and 21474836";
							}
						}
						configd:help "Generic ESTABLISHED timeout in seconds";
						configd:delete "/opt/vyatta/share/tmplscripts/system/session/timeout/other/established/configd_delete.sh";
						configd:update "/opt/vyatta/share/tmplscripts/system/session/timeout/other/established/configd_update.sh";
					}
					leaf new {
						type uint32 {
							range 1..21474836 {
								error-message "Value must be between 1 and 21474836";
							}
						}
						configd:help "Generic NEW timeout in seconds";
						configd:delete "/opt/vyatta/share/tmplscripts/system/session/timeout/other/new/configd_delete.sh";
						configd:update "/opt/vyatta/share/tmplscripts/system/session/timeout/other/new/configd_update.sh";
					}
				}
				container custom {
					presence "true";
					configd:help "Custom connection timeout options";
					list rule {
						configd:help "Rule number (1-9999)";
						configd:end "/opt/vyatta/share/tmplscripts/system/session/timeout/custom/rule/configd_end.sh";
						configd:validate "/opt/vyatta/share/tmplscripts/system/session/timeout/custom/rule/configd_validate1.cli";
						key "tagnode";
						leaf tagnode {
							type uint32 {
								range 1..9999 {
									error-message "rule number must be between 1 and 9999";
								}
							}
							configd:help "Rule number (1-9999)";
						}
						leaf expire {
							type uint32 {
								range 1..21474836 {
									error-message "Value must be between 1 and 21474836";
								}
							}
							configd:help "Expire time out value for this rule";
						}
						container source {
							presence "true";
							configd:help "Source parameters";
							leaf address {
								type string {
									configd:syntax "/opt/vyatta/share/tmplscripts/system/session/timeout/custom/rule/source/address/configd_syntax1.cli";
									configd:syntax "/opt/vyatta/share/tmplscripts/system/session/timeout/custom/rule/source/address/configd_syntax2.cli";
								}
								configd:help "Source IP address, subnet, or address-group";
								configd:allowed "/opt/vyatta/share/tmplscripts/system/session/timeout/custom/rule/source/address/configd_allowed.sh";
								configd:validate "/opt/vyatta/share/tmplscripts/system/session/timeout/custom/rule/source/address/configd_validate1.cli";
								configd:validate "/opt/vyatta/share/tmplscripts/system/session/timeout/custom/rule/source/address/configd_validate2.cli";
								configd:validate "/opt/vyatta/share/tmplscripts/system/session/timeout/custom/rule/source/address/configd_validate3.cli";
								configd:validate "/opt/vyatta/share/tmplscripts/system/session/timeout/custom/rule/source/address/configd_validate4.cli";
								configd:validate "/opt/vyatta/share/tmplscripts/system/session/timeout/custom/rule/source/address/configd_validate5.cli";
								configd:validate "/opt/vyatta/share/tmplscripts/system/session/timeout/custom/rule/source/address/configd_validate6.cli";
							}
							leaf port {
								type string;
								configd:help "Source port or port-group";
								configd:allowed "/opt/vyatta/share/tmplscripts/system/session/timeout/custom/rule/source/port/configd_allowed.sh";
								configd:validate "/opt/vyatta/share/tmplscripts/system/session/timeout/custom/rule/source/port/configd_validate1.cli";
								configd:validate "/opt/vyatta/share/tmplscripts/system/session/timeout/custom/rule/source/port/configd_validate2.cli";
							}
						}
						container destination {
							presence "true";
							configd:help "Destination parameters";
							leaf address {
								type string {
									configd:syntax "/opt/vyatta/share/tmplscripts/system/session/timeout/custom/rule/destination/address/configd_syntax1.cli";
									configd:syntax "/opt/vyatta/share/tmplscripts/system/session/timeout/custom/rule/destination/address/configd_syntax2.cli";
								}
								configd:help "Destination IP address, subnet, or address-group";
								configd:validate "/opt/vyatta/share/tmplscripts/system/session/timeout/custom/rule/destination/address/configd_validate1.cli";
								configd:validate "/opt/vyatta/share/tmplscripts/system/session/timeout/custom/rule/destination/address/configd_validate2.cli";
								configd:validate "/opt/vyatta/share/tmplscripts/system/session/timeout/custom/rule/destination/address/configd_validate3.cli";
								configd:validate "/opt/vyatta/share/tmplscripts/system/session/timeout/custom/rule/destination/address/configd_validate4.cli";
								configd:validate "/opt/vyatta/share/tmplscripts/system/session/timeout/custom/rule/destination/address/configd_validate5.cli";
							}
							leaf port {
								type string;
								configd:help "Destination port or port-group";
								configd:allowed "/opt/vyatta/share/tmplscripts/system/session/timeout/custom/rule/destination/port/configd_allowed.sh";
								configd:validate "/opt/vyatta/share/tmplscripts/system/session/timeout/custom/rule/destination/port/configd_validate1.cli";
								configd:validate "/opt/vyatta/share/tmplscripts/system/session/timeout/custom/rule/destination/port/configd_validate2.cli";
							}
						}
						leaf protocol {
							type string {
								configd:syntax "/opt/vyatta/share/tmplscripts/system/session/timeout/custom/rule/protocol/configd_syntax1.cli";
								configd:syntax "/opt/vyatta/share/tmplscripts/system/session/timeout/custom/rule/protocol/configd_syntax2.cli";
							}
							configd:help "Protocol to match";
							configd:allowed "/opt/vyatta/share/tmplscripts/system/session/timeout/custom/rule/protocol/configd_allowed.sh";
						}
					}
				}
				container udp {
					presence "true";
					configd:help "UDP timeout";
					leaf established {
						type uint32 {
							range 1..21474836 {
								error-message "Value must be between 1 and 21474836";
							}
						}
						configd:help "UDP ESTABLISHED timeout in seconds";
						configd:delete "/opt/vyatta/share/tmplscripts/system/session/timeout/udp/established/configd_delete.sh";
						configd:update "/opt/vyatta/share/tmplscripts/system/session/timeout/udp/established/configd_update.sh";
					}
					leaf new {
						type uint32 {
							range 1..21474836 {
								error-message "Value must be between 1 and 21474836";
							}
						}
						configd:help "UDP NEW timeout in seconds";
						configd:delete "/opt/vyatta/share/tmplscripts/system/session/timeout/udp/new/configd_delete.sh";
						configd:update "/opt/vyatta/share/tmplscripts/system/session/timeout/udp/new/configd_update.sh";
					}
				}
			}
		}
	}
}
