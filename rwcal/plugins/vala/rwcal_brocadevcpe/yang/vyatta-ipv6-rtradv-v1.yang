module vyatta-ipv6-rtradv-v1 {
	namespace "urn:vyatta.com:mgmt:vyatta-ipv6-rtradv:1";
	prefix vyatta-ipv6-rtradv-v1;

	import vyatta-types-v1 {
		prefix types;
	}
	import configd-v1 {
		prefix configd;
	}
	import vyatta-interfaces-v1 {
		prefix if;
	}
	import vyatta-interfaces-bridge-v1 {
		prefix interfaces-bridge;
	}
	import vyatta-interfaces-dataplane-v1 {
		prefix interfaces-dataplane;
	}
	import vyatta-interfaces-l2tpeth-v1 {
		prefix interfaces-l2tpeth;
	}
	import vyatta-interfaces-loopback-v1 {
		prefix interfaces-loopback;
	}
	import vyatta-interfaces-openvpn-v1 {
		prefix interfaces-openvpn;
	}
	import vyatta-interfaces-tunnel-v1 {
		prefix interfaces-tunnel;
	}
	import vyatta-interfaces-bonding-v1 {
		prefix interfaces-bonding;
	}

	organization "Brocade Communications Systems, Inc.";
	contact
		"Brocade Communications Systems, Inc.
		 Postal: 130 Holger Way
		         San Jose, CA 95134
		 E-mail: support@Brocade.com
		 Web: www.brocade.com";

	revision 2015-08-14 {
		description "Initial revision of version 1.";
	}

	typedef prefix-lifetime {
		type union {
			type enumeration {
				enum "infinity";
			}
			type uint32 {
				range 0..max;
			}
		}
	}

	grouping address-opts {
		leaf-list eui64 {
			type types:ipv6-prefix {
				pattern "[0-9a-fA-F]{1,4}(:[0-9a-fA-F]{1,4}){0,3}(::|(:0){4})/64" {
					error-message "Must be a valid prefix of length 64";
				}
			}
			ordered-by "user";
			configd:help "Assign IPv6 address using EUI-64 based on MAC address";
			configd:create "/opt/vyatta/sbin/vyatta-ipv6-eui64.pl  --create $VAR(../../../@) $VAR(@)";
			configd:delete "/opt/vyatta/sbin/vyatta-ipv6-eui64.pl  --delete $VAR(../../../@) $VAR(@)";
		}
		leaf autoconf {
			type empty;
			configd:help "Enable acquisition of IPv6 address using stateless autoconfig";
			configd:update "/opt/vyatta/sbin/vyatta-ipv6-autoconf.sh update  $VAR(../../../@)";
			configd:delete "/opt/vyatta/sbin/vyatta-ipv6-autoconf.sh delete  $VAR(../../../@)";
		}
		leaf link-local {
			type types:ipv6-address;
			configd:help "Set IPv6 link-local address";
			configd:update "/opt/vyatta/sbin/vyatta-ipv6-link-local.pl --update $VAR(../../../@) $VAR(@) --verbose";
			configd:delete "/opt/vyatta/sbin/vyatta-ipv6-link-local.pl --delete $VAR(../../../@) $VAR(@) --verbose";
		}
	}

	grouping ra-parameters {
		leaf retrans-timer {
			type uint32;
			configd:help "Value to place in \"Retrans Timer\" field in RAs.";
			default "0";
		}
		leaf link-mtu {
			type uint32 {
				range "0|1280..9000";
			}
			configd:help "Value of link MTU to place in RAs";
			default "0";
		}
		leaf min-interval {
			type uint32 {
				range 3..1350;
			}
			configd:help "Minimum interval between unsolicited multicast RAs";
		}
		leaf default-preference {
			type enumeration {
				enum "low" {
					configd:help "Default router is low preference";
				}
				enum "medium" {
					configd:help "Default router is medium preference (Default)";
				}
				enum "high" {
					configd:help "Default router is high preference";
				}
			}
			configd:help "Default router preference";
		}
		list prefix {
			configd:help "IPv6 prefix to be advertised in Router Advertisements (RAs)";
			key "tagnode";
			leaf tagnode {
				type types:ipv6-prefix;
				configd:help "IPv6 prefix to be advertised in Router Advertisements (RAs)";
			}
			leaf on-link-flag {
				type boolean;
				configd:help "Flag that prefix can be used for on-link determination";
				default "true";
			}
			leaf preferred-lifetime {
				type prefix-lifetime;
				configd:help "Time in seconds or infinity that the prefix will remain preferred";
			}
			leaf autonomous-flag {
				type boolean;
				configd:help "Whether prefix can be used for address auto-configuration";
				default "true";
			}
			leaf valid-lifetime {
				type prefix-lifetime;
				configd:help "Time in seconds or infinity that the prefix will remain valid";
				default "2592000";
			}
		}
		leaf cur-hop-limit {
			type uint32 {
				range 0..255;
			}
			configd:help "Value to be placed in the \"Current Hop Limit\" field in RAs";
			default "64";
		}
		leaf max-interval {
			type uint32 {
				range 4..1800;
			}
			configd:help "Maximum interval between unsolicited multicast RAs";
			default "600";
		}
		leaf managed-flag {
			type boolean;
			configd:help "Value for \"managed address configuration\" flag in RAs";
			default "false";
		}
		leaf send-advert {
			type boolean;
			configd:help "Enable/disable sending RAs";
			default "true";
		}
		leaf default-lifetime {
			type uint32 {
				range "0|4..9000";
			}
			configd:help "Value to be placed in \"Router Lifetime\" field in RAs";
		}
		leaf reachable-time {
			type uint32 {
				range 0..3600000;
			}
			configd:help "Value to be placed in \"Reachable Time\" field in RAs";
			default "0";
		}
		leaf other-config-flag {
			type boolean;
			configd:help "Value to be placed in the \"other configuration\" flag in RAs";
			default "false";
		}
	}

	grouping if-ipv6-parameters {
		leaf disable-forwarding {
			configd:priority "501";
			type empty;
			configd:help "Disable IPv6 forwarding on this interface";
			configd:create "/opt/vyatta/sbin/vyatta-ipv6-forwarding.sh create $VAR(../../@)";
			configd:delete "/opt/vyatta/sbin/vyatta-ipv6-forwarding.sh delete $VAR(../../@)";
		}
		leaf dup-addr-detect-transmits {
			configd:priority "501";
			type uint32 {
				range 0..max;
			}
			configd:help "Number of NS messages to send while performing DAD";
			configd:update "perl -e 'system \"sysctl -qw net/ipv6/conf/$VAR(../../@)/dad_transmits=$VAR(@)\" if -d \"/sys/class/net/$VAR(../../@)\"'";
			configd:delete "perl -e 'system \"sysctl -qw net/ipv6/conf/$VAR(../../@)/dad_transmits=1\" if -d \"/sys/class/net/$VAR(../../@)\"'";
			default "1";
		}
		container router-advert {
			presence "true";
			configd:priority "501";
			configd:help "Configure parameters for sending Router Advertisements (RAs)";
			configd:end "/opt/vyatta/sbin/vyatta-ipv6-rtradv.sh $VAR(../../@)";
			uses ra-parameters;
		}
		container address {
			presence "true";
			configd:help "IPv6 address auto-configuration modes";
			uses address-opts;
		}
	}

	grouping vif-ipv6-parameters {
		leaf disable-forwarding {
			configd:priority "501";
			type empty;
			configd:help "Disable IPv6 forwarding on this interface";
			configd:create "/opt/vyatta/sbin/vyatta-ipv6-forwarding.sh create $VAR(../../../@).$VAR(../../@)";
			configd:delete "/opt/vyatta/sbin/vyatta-ipv6-forwarding.sh delete $VAR(../../../@).$VAR(../../@)";
		}
		leaf dup-addr-detect-transmits {
			configd:priority "501";
			type uint32 {
				range 0..max;
			}
			configd:help "Number of NS messages to send while performing DAD";
			configd:update "sysctl -qw net/ipv6/conf/$VAR(../../../@).$VAR(../../@)/dad_transmits=$VAR(@)";
			configd:delete "sysctl -qw net/ipv6/conf/$VAR(../../../@).$VAR(../../@)/dad_transmits=1";
			default "1";
		}
		container router-advert {
			presence "true";
			configd:priority "501";
			configd:help "Configure parameters for sending Router Advertisements (RAs)";
			configd:end "/opt/vyatta/sbin/vyatta-ipv6-rtradv.sh $VAR(../../../@).$VAR(../../@)";
			uses ra-parameters;
		}
		container address {
			presence "true";
			configd:help "IPv6 address auto-configuration modes";
			uses address-opts {
				refine eui64 {
					configd:create "/opt/vyatta/sbin/vyatta-ipv6-eui64.pl  --create $VAR(../../../../@).$VAR(../../../@) $VAR(@)";
					configd:delete "/opt/vyatta/sbin/vyatta-ipv6-eui64.pl  --delete $VAR(../../../../@).$VAR(../../../@) $VAR(@)";
				}
				refine autoconf {
					configd:update "/opt/vyatta/sbin/vyatta-ipv6-autoconf.sh update  $VAR(../../../../@).$VAR(../../../@)";
					configd:delete "/opt/vyatta/sbin/vyatta-ipv6-autoconf.sh delete  $VAR(../../../../@).$VAR(../../../@)";
				}
				refine link-local {
					configd:update "/opt/vyatta/sbin/vyatta-ipv6-link-local.pl --update $VAR(../../../../@).$VAR(../../../@) $VAR(@) --verbose";
					configd:delete "/opt/vyatta/sbin/vyatta-ipv6-link-local.pl --delete $VAR(../../../../@).$VAR(../../../@) $VAR(@) --verbose";
				}
			}
		}
	}

	augment /if:interfaces/interfaces-bridge:bridge/interfaces-bridge:ipv6 {
		uses if-ipv6-parameters;
	}

	augment /if:interfaces/interfaces-dataplane:dataplane/interfaces-dataplane:ipv6 {
		uses if-ipv6-parameters;
	}

	augment /if:interfaces/interfaces-dataplane:dataplane/interfaces-dataplane:vif/interfaces-dataplane:ipv6 {
		uses vif-ipv6-parameters;
	}

	augment /if:interfaces/interfaces-l2tpeth:l2tpeth/interfaces-l2tpeth:ipv6 {
		uses if-ipv6-parameters;
	}
	augment /if:interfaces/interfaces-l2tpeth:l2tpeth/interfaces-l2tpeth:vif/interfaces-l2tpeth:ipv6 {
		uses vif-ipv6-parameters;
	}

	augment /if:interfaces/interfaces-loopback:loopback/interfaces-loopback:ipv6 {
		uses if-ipv6-parameters;
	}

	augment /if:interfaces/interfaces-openvpn:openvpn/interfaces-openvpn:ipv6 {
		uses if-ipv6-parameters;
	}

	augment /if:interfaces/interfaces-tunnel:tunnel/interfaces-tunnel:ipv6 {
		uses if-ipv6-parameters;
	}

	augment /if:interfaces/interfaces-bonding:bonding/interfaces-bonding:ipv6 {
		uses if-ipv6-parameters;
	}

	augment /if:interfaces/interfaces-bonding:bonding/interfaces-bonding:vif/interfaces-bonding:ipv6 {
		uses vif-ipv6-parameters;
	}
}
