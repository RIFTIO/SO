module ifmgrd-v1 {
	namespace "urn:vyatta.com:mgmt:ifmgrd:1";
	prefix ifmgrd;

	import vyatta-interfaces-v1 {
		prefix if;
	}

	import configd-v1 {
		prefix configd;
	}

	organization "Brocade Communications Systems, Inc.";
	contact
		"Brocade Communications Systems, Inc.
                 Postal: 130 Holger Way
                         San Jose, CA 95134
                 E-mail: support@Brocade.com
                 Web: www.brocade.com";

	revision 2015-09-29 {
		description "Initial revision.";
	}
	augment /if:interfaces {
		configd:end "ifmgrctl apply";
	}
}
