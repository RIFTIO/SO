module vyatta-interfaces-dataplane-unnumbered-v1 {
	namespace "urn:vyatta.com:mgmt:vyatta-interfaces-unnumbered:1";
	prefix vyatta-interfaces-dataplane-unnumbered-v1;

	import vyatta-types-v1 {
		prefix types;
	}
	import configd-v1 {
		prefix configd;
	}
	import vyatta-interfaces-v1 {
		prefix if;
	}
	import vyatta-interfaces-dataplane-v1 {
		prefix interfaces-dataplane;
	}

	organization "Brocade Communications Systems, Inc.";
	contact
		"Brocade Communications Systems, Inc.
		 Postal: 130 Holger Way
		         San Jose, CA 95134
		 E-mail: support@Brocade.com
		 Web: www.brocade.com";

	revision 2015-08-14 {
		description "Initial revision of version 1.";
	}

	grouping unnumbered-opts {
			list donor-interface {
				max-elements  "1";
				configd:help "donor interface name";
				configd:allowed "/opt/vyatta/share/tmplscripts/interfaces/dataplane/unnumbered/unnumbered-allowed.sh";
				key "tagnode";
				leaf tagnode {
					type union {
						type string {
							pattern "lo(|[1-9]([0-9]){0,4})";
							configd:pattern-help "<lo|loN>";
						}
						type interfaces-dataplane:dataplane-ifname;
					}
				}
				leaf preferred-address {
					type types:ipv4-address;
					configd:help "preferred address to use from donor interface";
					configd:allowed "/opt/vyatta/share/tmplscripts/interfaces/dataplane/unnumbered/preferred-address/configd_allowed.pl --donor-dev=$VAR(../@) --ipv4";
				}
				configd:validate "vyatta-interfaces.pl --valid-donor-commit $VAR(../../@) --dev $VAR(@@)";
			}
	}

	grouping unnumbered-opts-ipv6 {
			list donor-interface {
				max-elements  "1";
				configd:help "donor interface name";
				configd:allowed "/opt/vyatta/share/tmplscripts/interfaces/dataplane/unnumbered/unnumbered-allowed.sh";
				key "tagnode";
				leaf tagnode {
					type union {
						type string {
							pattern "lo(|[1-9]([0-9]){0,4})";
							configd:pattern-help "<lo|loN>";
						}
						type interfaces-dataplane:dataplane-ifname;
					}
				}
				leaf preferred-address {
					type types:ipv6-address;
					configd:help "preferred address to use from donor interface";
					configd:allowed "/opt/vyatta/share/tmplscripts/interfaces/dataplane/unnumbered/preferred-address/configd_allowed.pl --donor-dev=$VAR(../@) --ipv6";
				}
				configd:validate "vyatta-interfaces.pl --valid-donor-commit $VAR(../../@) --dev $VAR(@@)";
			}
	}

	augment /if:interfaces/interfaces-dataplane:dataplane/interfaces-dataplane:ip {
		container unnumbered {
			configd:help "Enable unnumbered IP";
			configd:priority "330";
			configd:end "/opt/vyatta/sbin/vyatta-update-unnumbered.pl --dev=$VAR(../../@)";
			configd:validate "vyatta-interfaces.pl --check_unnumbered $VAR(../@) --unnumbered_intf $VAR(../../@)";
			uses unnumbered-opts;
		}
	}
	augment /if:interfaces/interfaces-dataplane:dataplane/interfaces-dataplane:ipv6 {
		container unnumbered {
			configd:help "Enable unnumbered IPv6";
			configd:priority "330";
			configd:end "/opt/vyatta/sbin/vyatta-update-unnumbered.pl --dev=$VAR(../../@) --ipv6";
			configd:validate "vyatta-interfaces.pl --check_unnumbered $VAR(../@) --unnumbered_intf $VAR(../../@)";
			uses unnumbered-opts-ipv6;
		}
	}
	augment /if:interfaces/interfaces-dataplane:dataplane/interfaces-dataplane:vif/interfaces-dataplane:ip {
		container unnumbered {
			configd:help "Enable unnumbered IP";
			configd:priority "330";
			configd:end "/opt/vyatta/sbin/vyatta-update-unnumbered.pl --dev=$VAR(../../../@).$VAR(../../@)";
			configd:validate "vyatta-interfaces.pl --check_unnumbered $VAR(../@) --unnumbered_intf $VAR(../../../@).$VAR(../../@)";
			uses unnumbered-opts;
		}
	}
	augment /if:interfaces/interfaces-dataplane:dataplane/interfaces-dataplane:vif/interfaces-dataplane:ipv6 {
		container unnumbered {
			configd:help "Enable unnumbered IPv6";
			configd:priority "330";
			configd:end "/opt/vyatta/sbin/vyatta-update-unnumbered.pl --dev=$VAR(../../../@).$VAR(../../@) --ipv6";
			configd:validate "vyatta-interfaces.pl --check_unnumbered $VAR(../@) --unnumbered_intf $VAR(../../../@).$VAR(../../@)";
			uses unnumbered-opts-ipv6;
		}
	}
}
