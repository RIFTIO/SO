/*
 * 
 *   Copyright 2016 RIFT.IO Inc
 *
 *   Licensed under the Apache License, Version 2.0 (the "License");
 *   you may not use this file except in compliance with the License.
 *   You may obtain a copy of the License at
 *
 *       http://www.apache.org/licenses/LICENSE-2.0
 *
 *   Unless required by applicable law or agreed to in writing, software
 *   distributed under the License is distributed on an "AS IS" BASIS,
 *   WITHOUT WARRANTIES OR CONDITIONS OF ANY KIND, either express or implied.
 *   See the License for the specific language governing permissions and
 *   limitations under the License.
 *
 *
 */

module nsr-annotation
{
  namespace "http://riftio.com/ns/riftware-1.0/nsr-annotation";
  prefix "nsr-ann";

  import tailf-common {
    prefix tailf;
  }

  import nsr {
    prefix nsr;
  }

  tailf:annotate "/nsr:ns-instance-opdata" {
    tailf:callpoint rw_callpoint;
  }
  tailf:annotate "/nsr:exec-ns-service-primitive" {
     tailf:actionpoint rw_actionpoint;
  }
  tailf:annotate "/nsr:get-ns-service-primitive-values" {
     tailf:actionpoint rw_actionpoint;
  }
  tailf:annotate "/nsr:start-network-service" {
     tailf:actionpoint rw_actionpoint;
  }
}
