/*
 *
 *   Copyright 2016 RIFT.IO Inc
 *
 *   Licensed under the Apache License, Version 2.0 (the "License");
 *   you may not use this file except in compliance with the License.
 *   You may obtain a copy of the License at
 *
 *       http://www.apache.org/licenses/LICENSE-2.0
 *
 *   Unless required by applicable law or agreed to in writing, software
 *   distributed under the License is distributed on an "AS IS" BASIS,
 *   WITHOUT WARRANTIES OR CONDITIONS OF ANY KIND, either express or implied.
 *   See the License for the specific language governing permissions and
 *   limitations under the License.
 *
 *
 */

module rw-pkg-mgmt-annotation
{
  namespace "http://riftio.com/ns/riftware-1.0/rw-pkg-mgmt-annotation";
  prefix "rw-pkg-mgmt-ann";

  import rw-pkg-mgmt {
    prefix rw-pkg-mgmt;
  }

  import tailf-common {
    prefix tailf;
  }

  tailf:annotate "/rw-pkg-mgmt:download-jobs" {
    tailf:callpoint rw_callpoint;
  }

  tailf:annotate "/rw-pkg-mgmt:copy-jobs" {
    tailf:callpoint rw_callpoint;
  }

  tailf:annotate "/rw-pkg-mgmt:get-package-endpoint" {
     tailf:actionpoint rw_actionpoint;
  }

  tailf:annotate "/rw-pkg-mgmt:package-copy" {
     tailf:actionpoint rw_actionpoint;
  }

  tailf:annotate "/rw-pkg-mgmt:get-package-schema" {
     tailf:actionpoint rw_actionpoint;
  }

  tailf:annotate "/rw-pkg-mgmt:package-file-add" {
     tailf:actionpoint rw_actionpoint;
  }

  tailf:annotate "/rw-pkg-mgmt:package-file-delete" {
     tailf:actionpoint rw_actionpoint;
  }

  tailf:annotate "/rw-pkg-mgmt:package-create" {
     tailf:actionpoint rw_actionpoint;
  }

  tailf:annotate "/rw-pkg-mgmt:package-update" {
     tailf:actionpoint rw_actionpoint;
  }

  tailf:annotate "/rw-pkg-mgmt:package-export" {
     tailf:actionpoint rw_actionpoint;
  }
}
