/*
 * 
 *   Copyright 2016 RIFT.IO Inc
 *
 *   Licensed under the Apache License, Version 2.0 (the "License");
 *   you may not use this file except in compliance with the License.
 *   You may obtain a copy of the License at
 *
 *       http://www.apache.org/licenses/LICENSE-2.0
 *
 *   Unless required by applicable law or agreed to in writing, software
 *   distributed under the License is distributed on an "AS IS" BASIS,
 *   WITHOUT WARRANTIES OR CONDITIONS OF ANY KIND, either express or implied.
 *   See the License for the specific language governing permissions and
 *   limitations under the License.
 *
 *
 */

module rw-image-mgmt-annotation
{
  namespace "http://riftio.com/ns/riftware-1.0/rw-image-mgmt-annotation";
  prefix "rw-image-mgmt-ann";

  import rw-image-mgmt {
    prefix rw-image-mgmt;
  }

  import tailf-common {
    prefix tailf;
  }

  tailf:annotate "/rw-image-mgmt:upload-jobs" {
    tailf:callpoint rw_callpoint;
  }

  tailf:annotate "/rw-image-mgmt:create-upload-job" {
    tailf:actionpoint rw_actionpoint;
  }

  tailf:annotate "/rw-image-mgmt:cancel-upload-job" {
    tailf:actionpoint rw_actionpoint;
  }
}
